FME workspace WSDashboard.fmw

Parameters:
- Days_Back = 7   # Number of Days Back

Creator
    GEOMTYPE = Geometry Object
    NUM = 1
    CREATED -> PythonCaller
PythonCaller
    NEW_ATTRIBUTES = fromdate today
    PYTHONSOURCE:
      import fme
      import fmeobjects
      # Template Function interface:
      # When using this function, make sure its name is set as the value of
      # the 'Class or Function to Process Features' transformer parameter
      def processFeature(feature):

          from datetime import date, timedelta
          fromdate = date.today() - timedelta(days=7)
          feature.setAttribute('today', str(date.today()))
          feature.setAttribute('fromdate', str(fromdate))
          pass
    PYTHONSYMBOL = processFeature
    -> FeatureReader_CZS_EmailTransactions [INITIATOR]
    -> FeatureReader_CZS_FME_JOB_STATUS [INITIATOR]
FeatureReader_CZS_EmailTransactions
    ATTRIBUTES = private.email_transactions,"transaction_reference_number,filename,email_address,creation_timestamp,service,request_body,geometry_count,id,salesperson_id,item_subtotal,total,subscription_used,transaction_date,fob,po_number,terms,billing_address,shipping_address,format,coordsys,product_name,tax_subtotal,contact_name,whatif_item_subtotal,whatif_tax_subtotal,whatif_total,account_balance,subscription_expiration,parsed_data,clean_request,transaction_expiration,quote_reference_number,customer_id,format_code"
    ATTR_ACCUM_MODE = Only Use Result
    COMBINE_GEOM = Use Result
    DATASET = postgis-whitestar
    FEATURETYPES = private.email_transactions
    FORMAT = POSTGIS
    INTERACT = <No Spatial Filter>
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = postgis-whitestar
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    WHERE = creation_timestamp >= '@Value(fromdate)' AND creation_timestamp < '@Value(today)'
    private.email_transactions -> DatabaseJoiner_CustomerID_2
DatabaseJoiner_CustomerID_2
    ADDED_FIELDS = customer_id
    ATTR_ACCUM_MODE = Merge Joined
    ATTR_CONFLICT_RES = Use Original
    CACHE_SIZE = 5000
    DATASET = postgis-whitestar
    FORMAT = POSTGIS
    JOIN_KEYS = email_address email_address
    MATCH_RULE_DISPLAY = Must Match Exactly One (1:1)
    POSTGIS_CREATE_FEATURE_TABLES_FROM_DATA = Yes
    POSTGIS_DISABLE_COLLECTION_SPLITTING = yes
    POSTGIS_NAMED_CONNECTION = postgis-whitestar
    POSTGIS_QUERY_FEATURE_TYPES_FOR_MERGE_FILTERS = Yes
    POSTGIS_READ_TIME_WITH_TIMEZONE = Yes
    POSTGIS_USE_TRUE_POSTGIS_TYPES = yes
    PREFETCH_EXHAUSTIVE = Yes
    TABLE = private.authorized_emails
    JOINED -> DatabaseJoiner_Customer_Name_2
DatabaseJoiner_Customer_Name_2
    ADDED_FIELDS = customer_name
    ATTR_ACCUM_MODE = Merge Joined
    ATTR_CONFLICT_RES = Use Original
    CACHE_SIZE = 5000
    DATASET = postgis-whitestar
    FORMAT = POSTGIS
    JOIN_KEYS = customer_id id
    MATCH_RULE_DISPLAY = Must Match Exactly One (1:1)
    POSTGIS_CREATE_FEATURE_TABLES_FROM_DATA = Yes
    POSTGIS_DISABLE_COLLECTION_SPLITTING = yes
    POSTGIS_NAMED_CONNECTION = postgis-whitestar
    POSTGIS_QUERY_FEATURE_TYPES_FOR_MERGE_FILTERS = Yes
    POSTGIS_READ_TIME_WITH_TIMEZONE = Yes
    POSTGIS_USE_TRUE_POSTGIS_TYPES = yes
    PREFETCH_EXHAUSTIVE = Yes
    TABLE = private.customers
    JOINED -> ChartGenerator
ChartGenerator
    AXES_FONT = Arial,12
    AXES_LW = 0.5
    BACKGROUND_COLOR = 1,1,1
    CHART_SETUP = DATAATT;product_name;LABATT;;COLOR;0,0,1;LABEL_ANGLE;S;BAR_ORIENTATION;V;BAR_STACKING;NO;FME_CONTROLLER_QUERY_FILE;transformers/dependencies/charter/Bar.fme
    CHART_TYPE = Bar
    DPI = 300
    INTERPRETATION = RGBA32
    LEGEND_OPTIONS = NO
    MULTI_DS = NO
    TICKS = T
    TICK_FONT = Arial,10
    TITLE_FONT = Arial,12
    X_INCH = 2.0
    X_LOG = LIN
    Y_INCH = 2.0
    Y_LOG = LIN
FeatureReader_CZS_FME_JOB_STATUS
    ATTRIBUTES = private.fme_job_status,"id,environment,fme_server_job_id,customer_email,product,request_type,format,request_details,file_root,parsed,processed,features_written_ffs,written,status,error"
    ATTR_ACCUM_MODE = Only Use Result
    COMBINE_GEOM = Use Result
    DATASET = postgis-whitestar
    FEATURETYPES = private.fme_job_status
    FORMAT = POSTGIS
    INTERACT = <No Spatial Filter>
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = postgis-whitestar
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    WHERE = parsed >= '@Value(fromdate)' AND parsed < '@Value(today)'
    private.fme_job_status -> DatabaseJoiner_CustomerID
DatabaseJoiner_CustomerID
    ADDED_FIELDS = customer_id
    ATTR_ACCUM_MODE = Merge Joined
    ATTR_CONFLICT_RES = Use Original
    CACHE_SIZE = 5000
    DATASET = postgis-whitestar
    FORMAT = POSTGIS
    JOIN_KEYS = customer_email email_address
    MATCH_RULE_DISPLAY = Must Match Exactly One (1:1)
    POSTGIS_CREATE_FEATURE_TABLES_FROM_DATA = Yes
    POSTGIS_DISABLE_COLLECTION_SPLITTING = yes
    POSTGIS_NAMED_CONNECTION = postgis-whitestar
    POSTGIS_QUERY_FEATURE_TYPES_FOR_MERGE_FILTERS = Yes
    POSTGIS_READ_TIME_WITH_TIMEZONE = Yes
    POSTGIS_USE_TRUE_POSTGIS_TYPES = yes
    PREFETCH_EXHAUSTIVE = Yes
    TABLE = private.authorized_emails
    JOINED -> DatabaseJoiner_Customer_Name
DatabaseJoiner_Customer_Name
    ADDED_FIELDS = customer_name
    ATTR_ACCUM_MODE = Merge Joined
    ATTR_CONFLICT_RES = Use Original
    CACHE_SIZE = 5000
    DATASET = postgis-whitestar
    FORMAT = POSTGIS
    JOIN_KEYS = customer_id id
    MATCH_RULE_DISPLAY = Must Match Exactly One (1:1)
    POSTGIS_CREATE_FEATURE_TABLES_FROM_DATA = Yes
    POSTGIS_DISABLE_COLLECTION_SPLITTING = yes
    POSTGIS_NAMED_CONNECTION = postgis-whitestar
    POSTGIS_QUERY_FEATURE_TYPES_FOR_MERGE_FILTERS = Yes
    POSTGIS_READ_TIME_WITH_TIMEZONE = Yes
    POSTGIS_USE_TRUE_POSTGIS_TYPES = yes
    PREFETCH_EXHAUSTIVE = Yes
    TABLE = private.customers
    JOINED -> ChartGenerator_2
    JOINED -> StatisticsCalculator_Format
    JOINED -> StatisticsCalculator_Format_2
    JOINED -> AttributeManager
ChartGenerator_2
    AXES_LW = 0.5
    BACKGROUND_COLOR = 1,1,1
    CHART_SETUP = SUMMARY_DATA;format;LABEL_ATTR;;COLOR_SCHEME;D;PCTLABELS;NO;EFFECTS;N;FME_CONTROLLER_QUERY_FILE;transformers/dependencies/charter/Pie.fme
    CHART_TYPE = Pie
    DPI = 300
    INTERPRETATION = RGBA32
    LEGEND_OPTIONS = NO
    TITLE_FONT = Arial,12
    X_INCH = 2.0
    Y_INCH = 2.0
StatisticsCalculator_Format
    COMPUTE_HISTOGRAM = NO
    COUNT_ATTR = _count
    GROUP_BY = format
    MAX_ATTR = _max
    MEAN_ATTR = _mean
    MIN_ATTR = _min
    PREPEND_ATTR_NAME_CHOICE = For multiple results only
    STATS_ATTRS = format
    SUM_ATTR = _sum
    SUMMARY -> HTMLReportGenerator
HTMLReportGenerator
    CONTENT_LIST = CHART_PIE
    PAGE_CONFIG = CHART_PIE{{LABEL;format;DATA;_count;COLOR;RED;FME_CONTROLLER_QUERY_FILE;transformers/dependencies/html5/Chart (Pie).fme}}
    -> AttributeCreator
AttributeCreator
    ATTR_TABLE:
      SET_TO grid_row = 0
      SET_TO grid_col = 0
    -> HTMLLayouter
StatisticsCalculator_Format_2
    COMPUTE_HISTOGRAM = NO
    COUNT_ATTR = _count
    GROUP_BY = customer_name
    MAX_ATTR = _max
    MEAN_ATTR = _mean
    MIN_ATTR = _min
    PREPEND_ATTR_NAME_CHOICE = For multiple results only
    STATS_ATTRS = format features_written_ffs
    SUM_ATTR = _sum
    SUMMARY -> HTMLReportGenerator_2
HTMLReportGenerator_2
    CONTENT_LIST = CHART_PIE
    PAGE_CONFIG = CHART_PIE{{LABEL;customer_name;DATA;features_written_ffs._sum;COLOR;RED;FME_CONTROLLER_QUERY_FILE;transformers/dependencies/html5/Chart (Pie).fme}}
    -> AttributeCreator_3
AttributeCreator_3
    ATTR_TABLE:
      SET_TO grid_row = 1
      SET_TO grid_col = 0
    -> HTMLLayouter
AttributeManager
    ATTR_TABLE = SET_TO day = @DateTimeFormat(@Value(parsed),  %Y-%m-%d-%a)
    -> StatisticsCalculator_Format_3
StatisticsCalculator_Format_3
    COMPUTE_HISTOGRAM = NO
    COUNT_ATTR = _count
    GROUP_BY = day
    MAX_ATTR = _max
    MEAN_ATTR = _mean
    MIN_ATTR = _min
    PREPEND_ATTR_NAME_CHOICE = For multiple results only
    STATS_ATTRS = features_written_ffs
    SUM_ATTR = _sum
    SUMMARY -> HTMLReportGenerator_3
HTMLReportGenerator_3
    CONTENT_LIST = CHART_LINE
    PAGE_CONFIG = CHART_LINE{{X_LABEL;date;r;day;Y_LABEL;;TABLE;_count|0,0,255;FME_CONTROLLER_QUERY_FILE;transformers/dependencies/html5/Chart (Line).fme}}
    -> AttributeCreator_2
AttributeCreator_2
    ATTR_TABLE:
      SET_TO grid_row = 3
      SET_TO grid_col = 1
    -> HTMLLayouter
HTMLLayouter
    COLUMN = @Value(grid_col)
    DIV_STYLE = SOLID
    LAYOUT = GRID
    ROW = @Value(grid_row)
    TITLE = Dashboard from @DateTimeNow() - @DateTimeAdd(@DateTimeNow(),-$(Days_Back))
    -> FeatureWriter [HTML]
FeatureWriter
    DATASET = /Users/fuad/Desktop/dashtest.html
    DATASET_ATTR = _dataset
    FEATURE_TYPE_LIST_ATTR = _feature_type
    FORMAT = HTML
    TOTAL_FEATURES_WRITTEN_ATTR = _total_features_written
