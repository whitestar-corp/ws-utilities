FME workspace permits_water.fmw

Parameters:
- DestDataset_POSTGIS = pg.whitestar.com   # Connection

Writers:
- POSTGIS_1: POSTGIS to $(DestDataset_POSTGIS)

SQLCreator_3
    COORDSYS = LL27
    DATASET = pg.whitestar.com
    EXPOSED_ATTRIBUTE_LIST = api,api_cnty,api_state,county,state,wstar_id
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select *
      from tx_header_pre_cum
      where length(api) = 8
    RESULT -> FeatureJoiner [LEFT]
SQLCreator_2
    DATASET = pg.whitestar.com
    EXPOSED_ATTRIBUTE_LIST = api,csg_dtr_cd,fresh_cntr,twdb_date,uqwp_from,uqwp_to
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT:
      select distinct
      wb_api as api,
      wb_fresh_water_cntr as fresh_cntr,
      wb_twdb_date as twdb_date,
      wb_surace_casing_deter_code as csg_dtr_cd,
      wb_uqwp_from as uqwp_from,
      wb_uqwp_to as uqwp_to
      from wb11
    RESULT -> FeatureJoiner [RIGHT]
FeatureJoiner
    ATTR_CONFLICT_RES = Use Left
    GEOMETRY_HANDLING = Use Left
    JOIN_KEYS = api api AUTO
    JOIN_MODE = Inner
    JOINED -> StringLengthCalculator_3
AttributeCreator_4
    ATTR_TABLE = SET_TO api = @Value(wstar_id)
    -> Sorter
Sorter
    SORT_PARM = api ALPHA ASCENDING fresh_cntr NUMERIC ASCENDING
    SORTED -> tx_water_latest_build (writer POSTGIS_1)
tx_water_latest_build (writer POSTGIS_1)
    attributes: wstar_id varchar(14),BTree, api varchar(14),BTree, api_state int2, api_cnty int2,BTree, state char(2), county varchar(25),BTree, fresh_cntr int2, twdb_date date, csg_dtr_cd char(1), uqwp_from int4, uqwp_to int4

Bookmark: wstar_id Check/Correct
StringLengthCalculator_3
    LENGTH_ATTR = _length_wstar_id
    SRC_ATTR = wstar_id
    -> Tester_2
Tester_2
    BOOL_OP = OR
    COMPOSITE_TEST = 1
    TEST_CLAUSE = TEST @Value(_length_wstar_id) < 14
    TEST_MODE = TEST
    PASSED -> StringPadder_3
    FAILED -> AttributeCreator_4
StringPadder_3
    BLANK_ATTRIBUTE = Yes
    PADCHAR = 0
    SIDE = Right
    SRC_ATTRS = wstar_id
    WIDTH = 14
    <REJECTED> -> AttributeCreator_4
