FME workspace loadp5.fmw

Parameters:
- SourceDataset_CSV2 = D:\Users\rwhite\Documents\texas-wells\wells-service\data\operator\p501.csv   # Source CSV (Comma Separated Value) File(s)
- DestDataset_POSTGRES = pg.whitestar.com   # Connection

Readers:
- CSV2_1: CSV2 from $(SourceDataset_CSV2)

Writers:
- POSTGRES_2: POSTGRES to $(DestDataset_POSTGRES)

CSV (reader CSV2_1)
    attributes: oror_org_operator_number string, oror_org_orgnization_name string, oror_refiling_required_flag string, oror_p5_status string, oror_hold_mail_code string, oror_renewal_letter_code string, oror_organization_code string, oror_organ_other_comment string, oror_gatherer_code string, oror_org_addr_line1 string, oror_org_addr_line2 string, oror_org_add_city string, oror_org_addr_state string, oror_org_addr_zip string, oror_org_addr_zip_suffix string, oror_location_addr_line1 string, oror_location_addr_line2 string, oror_location_addr_city string, oror_location_addr_state string, oror_location_addr_zip string, oror_location_addr_suffix string, oror_date_built string, oror_date_inactive string, oror_phone_number string, oror_refile_notice_month string, oror_refile_letter_date string, oror_refile_notice_date string, oror_refile_received_date string, oror_last_p5_received_date string, oror_other_organization_no string,
      oror_filing_problem_date string, oror_filing_problem_ltr_code string, oror_telephone_verify_flag string, oror_op_num_multi_used_flag string, oror_oil_gatherer_status string, oror_gas_gatherer_status string, oror_tax_cert string, oror_emer_phone_number string
    -> p501 (writer POSTGRES_2)
p501 (writer POSTGRES_2)
    attributes: oror_org_operator_number varchar(6),BTree, oror_org_orgnization_name varchar(32), oror_refiling_required_flag char(1), oror_p5_status char(1), oror_hold_mail_code char(1), oror_renewal_letter_code char(1), oror_organization_code char(1), oror_organ_other_comment varchar(20), oror_gatherer_code varchar(5), oror_org_addr_line1 varchar(31), oror_org_addr_line2 varchar(31), oror_org_add_city varchar(13), oror_org_addr_state char(2), oror_org_addr_zip char(5), oror_org_addr_zip_suffix char(4), oror_location_addr_line1 varchar(31), oror_location_addr_line2 varchar(31), oror_location_addr_city varchar(13), oror_location_addr_state char(2), oror_location_addr_zip char(5), oror_location_addr_suffix char(4), oror_date_built date, oror_date_inactive date, oror_phone_number varchar(10), oror_refile_notice_month int2, oror_refile_letter_date date, oror_refile_notice_date date, oror_refile_received_date date, oror_last_p5_received_date date, oror_other_organization_no varchar(6),BTree,
      oror_filing_problem_date date, oror_filing_problem_ltr_code char(3), oror_telephone_verify_flag char(1), oror_op_num_multi_used_flag char(1), oror_oil_gatherer_status char(1), oror_gas_gatherer_status char(1), oror_tax_cert char(1), oror_emer_phone_number varchar(10)
