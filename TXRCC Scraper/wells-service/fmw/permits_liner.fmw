FME workspace permits_liner.fmw

Parameters:
- DestDataset_POSTGIS_9 = pg.whitestar.com   # Connection

Writers:
- POSTGIS_1: POSTGIS to $(DestDataset_POSTGIS_9) in LL27

SQLCreator_3
    COORDSYS = LL27
    DATASET = pg.whitestar.com
    EXPOSED_ATTRIBUTE_LIST = api,api_cnty,api_state,county,state,wstar_id
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select *
      from tx_header_pre_cum
      where length(api) = 8
    RESULT -> FeatureJoiner [LEFT]
SQLCreator_2
    DATASET = pg.whitestar.com
    EXPOSED_ATTRIBUTE_LIST = api,btm_liner,lnr_count,lnr_frac_d,lnr_frac_n,lnr_thick,sacks_cmnt,top_liner
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT:
      select distinct
      wb_api as api,
      wb_line_count as lnr_count,
      wb_top_of_liner as top_liner,
      wb_bottom_of_liner as btm_liner,
      wb_lin_inch as lnr_thick,
      wb_lin_frac_denom as lnr_frac_d,
      wb_lin_frac_num as lnr_frac_n,
      wb_sacks_of_cement as sacks_cmnt
      from wb08
    RESULT -> FeatureJoiner [RIGHT]
FeatureJoiner
    ATTR_CONFLICT_RES = Use Left
    GEOMETRY_HANDLING = Use Left
    JOIN_KEYS = api api AUTO
    JOIN_MODE = Inner
    JOINED -> StringLengthCalculator_3
AttributeCreator_4
    ATTR_TABLE = SET_TO api = @Value(wstar_id)
    -> Sorter
Sorter
    SORT_PARM = api ALPHA ASCENDING lnr_count NUMERIC ASCENDING
    SORTED -> tx_liners_latest_build (writer POSTGIS_1)
tx_liners_latest_build (writer POSTGIS_1)
    attributes: wstar_id varchar(14),BTree, api varchar(14),BTree, api_state int2, api_cnty int2,BTree, state varchar(2), county varchar(25),BTree, lnr_count int2, lnr_thick int2, lnr_frac_n int2, lnr_frac_d int2, sacks_cmnt int4, top_liner int4, btm_liner int4

Bookmark: wstar_id Check/Correct
StringLengthCalculator_3
    LENGTH_ATTR = _length_wstar_id
    SRC_ATTR = wstar_id
    -> Tester_2
Tester_2
    BOOL_OP = OR
    COMPOSITE_TEST = 1
    TEST_CLAUSE = TEST @Value(_length_wstar_id) < 14
    TEST_MODE = TEST
    PASSED -> StringPadder_3
    FAILED -> AttributeCreator_4
StringPadder_3
    BLANK_ATTRIBUTE = Yes
    PADCHAR = 0
    SIDE = Right
    SRC_ATTRS = wstar_id
    WIDTH = 14
    <REJECTED> -> AttributeCreator_4
