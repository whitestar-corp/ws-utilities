FME workspace wb2pg.fmw

Parameters:
- DestDataset_POSTGRES = pg.whitestar.com   # Connection
- SourceDataset_CSV2_33 = D:\Users\rwhite\Documents\texas-wells\wells-service\data\wellbore\wb02.csv   # Source CSV (Comma Separated Value) File(s)
- DestDataset_POSTGRES_33 = pg.whitestar.com   # Connection
- SourceDataset_CSV2_49 = D:\Users\rwhite\Documents\texas-wells\wells-service\data\wellbore\wb03.csv   # Source CSV (Comma Separated Value) File(s)
- DestDataset_POSTGRES_49 = pg.whitestar.com   # Connection
- DestDataset_POSTGRES_41 = pg.whitestar.com   # Connection
- SourceDataset_CSV2_41 = D:\Users\rwhite\Documents\texas-wells\wells-service\data\wellbore\wb04.csv   # Source CSV (Comma Separated Value) File(s)
- SourceDataset_CSV2_29 = D:\Users\rwhite\Documents\texas-wells\wells-service\data\wellbore\wb05.csv   # Source CSV (Comma Separated Value) File(s)
- DestDataset_POSTGRES_29 = pg.whitestar.com   # Connection
- DestDataset_POSTGRES_37 = pg.whitestar.com   # Connection
- SourceDataset_CSV2_45 = D:\Users\rwhite\Documents\texas-wells\wells-service\data\wellbore\wb06.csv   # Source CSV (Comma Separated Value) File(s)
- SourceDataset_CSV2_37 = D:\Users\rwhite\Documents\texas-wells\wells-service\data\wellbore\wb07.csv   # Source CSV (Comma Separated Value) File(s)
- SourceDataset_CSV2_53 = D:\Users\rwhite\Documents\texas-wells\wells-service\data\wellbore\wb08.csv   # Source CSV (Comma Separated Value) File(s)
- DestDataset_POSTGRES_53 = pg.whitestar.com   # Connection
- SourceDataset_CSV2_31 = D:\Users\rwhite\Documents\texas-wells\wells-service\data\wellbore\wb09.csv   # Source CSV (Comma Separated Value) File(s)
- DestDataset_POSTGRES_31 = pg.whitestar.com   # Connection
- SourceDataset_CSV2_35 = D:\Users\rwhite\Documents\texas-wells\wells-service\data\wellbore\wb10.csv   # Source CSV (Comma Separated Value) File(s)
- DestDataset_POSTGRES_35 = pg.whitestar.com   # Connection
- SourceDataset_CSV2_39 = D:\Users\rwhite\Documents\texas-wells\wells-service\data\wellbore\wb11.csv   # Source CSV (Comma Separated Value) File(s)
- DestDataset_POSTGRES_39 = pg.whitestar.com   # Connection
- SourceDataset_CSV2_43 = D:\Users\rwhite\Documents\texas-wells\wells-service\data\wellbore\wb12.csv   # Source CSV (Comma Separated Value) File(s)
- DestDataset_POSTGRES_43 = pg.whitestar.com   # Connection
- SourceDataset_CSV2_47 = D:\Users\rwhite\Documents\texas-wells\wells-service\data\wellbore\wb13.csv   # Source CSV (Comma Separated Value) File(s)
- DestDataset_POSTGRES_47 = pg.whitestar.com   # Connection
- DestDataset_POSTGRES_51 = pg.whitestar.com   # Connection
- SourceDataset_CSV2_51 = D:\Users\rwhite\Documents\texas-wells\wells-service\data\wellbore\wb14.csv   # Source CSV (Comma Separated Value) File(s)
- SourceDataset_CSV2_28 = D:\Users\rwhite\Documents\texas-wells\wells-service\data\wellbore\wb15.csv   # Source CSV (Comma Separated Value) File(s)
- DestDataset_POSTGRES_55 = pg.whitestar.com   # Connection
- SourceDataset_CSV2_30 = D:\Users\rwhite\Documents\texas-wells\wells-service\data\wellbore\wb16.csv   # Source CSV (Comma Separated Value) File(s)
- DestDataset_POSTGRES_30 = pg.whitestar.com   # Connection
- SourceDataset_CSV2_32 = D:\Users\rwhite\Documents\texas-wells\wells-service\data\wellbore\wb17.csv   # Source CSV (Comma Separated Value) File(s)
- DestDataset_POSTGRES_32 = pg.whitestar.com   # Connection
- SourceDataset_CSV2_34 = D:\Users\rwhite\Documents\texas-wells\wells-service\data\wellbore\wb18.csv   # Source CSV (Comma Separated Value) File(s)
- DestDataset_POSTGRES_34 = pg.whitestar.com   # Connection
- SourceDataset_CSV2_36 = D:\Users\rwhite\Documents\texas-wells\wells-service\data\wellbore\wb19.csv   # Source CSV (Comma Separated Value) File(s)
- DestDataset_POSTGRES_36 = pg.whitestar.com   # Connection
- SourceDataset_CSV2_38 = D:\Users\rwhite\Documents\texas-wells\wells-service\data\wellbore\wb20.csv   # Source CSV (Comma Separated Value) File(s)
- DestDataset_POSTGRES_38 = pg.whitestar.com   # Connection
- DestDataset_POSTGRES_40 = pg.whitestar.com   # Connection
- DestDataset_POSTGRES_42 = pg.whitestar.com   # Connection
- SourceDataset_CSV2_42 = D:\Users\rwhite\Documents\texas-wells\wells-service\data\wellbore\wb21.csv   # Source CSV (Comma Separated Value) File(s)
- SourceDataset_CSV2_40 = D:\Users\rwhite\Documents\texas-wells\wells-service\data\wellbore\wb22.csv   # Source CSV (Comma Separated Value) File(s)
- DestDataset_POSTGRES_44 = pg.whitestar.com   # Connection
- SourceDataset_CSV2_44 = D:\Users\rwhite\Documents\texas-wells\wells-service\data\wellbore\wb23.csv   # Source CSV (Comma Separated Value) File(s)
- DestDataset_POSTGRES_46 = pg.whitestar.com   # Connection
- SourceDataset_CSV2_46 = D:\Users\rwhite\Documents\texas-wells\wells-service\data\wellbore\wb24.csv   # Source CSV (Comma Separated Value) File(s)
- DestDataset_POSTGRES_48 = pg.whitestar.com   # Connection
- SourceDataset_CSV2_48 = D:\Users\rwhite\Documents\texas-wells\wells-service\data\wellbore\wb25.csv   # Source CSV (Comma Separated Value) File(s)
- DestDataset_POSTGRES_50 = pg.whitestar.com   # Connection
- SourceDataset_CSV2_50 = D:\Users\rwhite\Documents\texas-wells\wells-service\data\wellbore\wb26.csv   # Source CSV (Comma Separated Value) File(s)
- DestDataset_POSTGRES_52 = pg.whitestar.com   # Connection
- DestDataset_POSTGRES_54 = pg.whitestar.com   # Connection
- SourceDataset_CSV2_52 = D:\Users\rwhite\Documents\texas-wells\wells-service\data\wellbore\wb27.csv   # Source CSV (Comma Separated Value) File(s)
- SourceDataset_CSV2 = D:\Users\rwhite\Documents\texas-wells\wells-service\data\wellbore\wb01.csv   # Source CSV (Comma Separated Value) File(s)

Readers:
- CSV2_1: CSV2 from $(SourceDataset_CSV2_33)
- CSV2_2: CSV2 from $(SourceDataset_CSV2_49)
- CSV2_3: CSV2 from $(SourceDataset_CSV2_41)
- CSV2_4: CSV2 from $(SourceDataset_CSV2_29)
- CSV2_5: CSV2 from $(SourceDataset_CSV2_45)
- CSV2_6: CSV2 from $(SourceDataset_CSV2_37)
- CSV2_7: CSV2 from $(SourceDataset_CSV2_53)
- CSV2_8: CSV2 from $(SourceDataset_CSV2_31)
- CSV2_9: CSV2 from $(SourceDataset_CSV2_35)
- CSV2_10: CSV2 from $(SourceDataset_CSV2_39)
- CSV2_11: CSV2 from $(SourceDataset_CSV2_43)
- CSV2_12: CSV2 from $(SourceDataset_CSV2_47)
- CSV2_13: CSV2 from $(SourceDataset_CSV2_51)
- CSV2_14: CSV2 from $(SourceDataset_CSV2_28)
- CSV2_15: CSV2 from $(SourceDataset_CSV2_30)
- CSV2_16: CSV2 from $(SourceDataset_CSV2_32)
- CSV2_17: CSV2 from $(SourceDataset_CSV2_34)
- CSV2_18: CSV2 from $(SourceDataset_CSV2_36)
- CSV2_19: CSV2 from $(SourceDataset_CSV2_38)
- CSV2_20: CSV2 from $(SourceDataset_CSV2_42)
- CSV2_21: CSV2 from $(SourceDataset_CSV2_40)
- CSV2_22: CSV2 from $(SourceDataset_CSV2_44)
- CSV2_23: CSV2 from $(SourceDataset_CSV2_46)
- CSV2_24: CSV2 from $(SourceDataset_CSV2_48)
- CSV2_25: CSV2 from $(SourceDataset_CSV2_50)
- CSV2_26: CSV2 from $(SourceDataset_CSV2_52)
- CSV2_27: CSV2 from $(SourceDataset_CSV2)

Writers:
- POSTGRES_1: POSTGRES to $(DestDataset_POSTGRES)
- POSTGRES_2: POSTGRES to $(DestDataset_POSTGRES_33)
- POSTGRES_3: POSTGRES to $(DestDataset_POSTGRES_49)
- POSTGRES_4: POSTGRES to $(DestDataset_POSTGRES_41)
- POSTGRES_5: POSTGRES to $(DestDataset_POSTGRES_29)
- POSTGRES_6: POSTGRES to $(DestDataset_POSTGRES_37)
- POSTGRES_7: POSTGRES to $(DestDataset_POSTGRES_53)
- POSTGRES_8: POSTGRES to $(DestDataset_POSTGRES_31)
- POSTGRES_9: POSTGRES to $(DestDataset_POSTGRES_35)
- POSTGRES_10: POSTGRES to $(DestDataset_POSTGRES_39)
- POSTGRES_11: POSTGRES to $(DestDataset_POSTGRES_43)
- POSTGRES_12: POSTGRES to $(DestDataset_POSTGRES_47)
- POSTGRES_13: POSTGRES to $(DestDataset_POSTGRES_51)
- POSTGRES_14: POSTGRES to $(DestDataset_POSTGRES_55)
- POSTGRES_15: POSTGRES to $(DestDataset_POSTGRES_30)
- POSTGRES_16: POSTGRES to $(DestDataset_POSTGRES_32)
- POSTGRES_17: POSTGRES to $(DestDataset_POSTGRES_34)
- POSTGRES_18: POSTGRES to $(DestDataset_POSTGRES_36)
- POSTGRES_19: POSTGRES to $(DestDataset_POSTGRES_38)
- POSTGRES_20: POSTGRES to $(DestDataset_POSTGRES_40)
- POSTGRES_21: POSTGRES to $(DestDataset_POSTGRES_42)
- POSTGRES_22: POSTGRES to $(DestDataset_POSTGRES_44)
- POSTGRES_23: POSTGRES to $(DestDataset_POSTGRES_46)
- POSTGRES_24: POSTGRES to $(DestDataset_POSTGRES_48)
- POSTGRES_25: POSTGRES to $(DestDataset_POSTGRES_50)
- POSTGRES_26: POSTGRES to $(DestDataset_POSTGRES_52)
- POSTGRES_27: POSTGRES to $(DestDataset_POSTGRES_54)

wb02 (writer POSTGRES_2)
    attributes: wb_api varchar(8),BTree, wb_og_code char(1), wb_oil_dist char(2), wb_oil_lse_nbr varchar(5), wb_oil_well_nbr varchar(6), wb_gas_rrc varchar(6), wb_gas_dist varchar(2), wb_gas_well_no varchar(6), wb_multi_well_rec_nbr varchar(2), wb_api_suffix varchar(2), wb_active_inactive_code char(1), wb_dwn_hole_commingle_code char(1), wb_created_from_pi_flag char(1), wb_rule_37_nbr varchar(20), wb_p_15 char(1), wb_p_12 char(1), wb_plug_date_ptr date
wb03 (writer POSTGRES_3)
    attributes: wb_api varchar(8),BTree, wb_file_key varchar(8), wb_file_date date, wb_except_rule_11 char(1), wb_cement_affidavit char(1), wb_g_5 char(1), wb_w_12 char(1), wb_dir_survey char(1), wb_w2_g1_date date, wb_compl_date date, wb_drl_compl_date date, wb_plugb_depth1 int4, wb_plugb_depth2 int4, wb_water_injection_nbr varchar(6), wb_salt_wtr varchar(5), wb_remarks char(1), wb_elevation int2, wb_elevation_code char(2), wb_log_file_rba numeric(8,0), wb_docket_nbr varchar(10), wb_psa_well_flag char(1), wb_allocation_well_flag char(1)
wb04 (writer POSTGRES_4)
    attributes: wb_api varchar(8),BTree, wb_rmk_line_cnt int2, wb_rmk_type_code char(1), wb_remarks varchar(70)
wb05 (writer POSTGRES_5)
    attributes: wb_api varchar(8),BTree, wb_segment_counter int2, wb_tubing_inches int2, wb_tubing_numerator int2, wb_tubing_denominator int2, wb_depth_set int2, wb_packer_set int4
wb06 (writer POSTGRES_6)
    attributes: wb_api varchar(8),BTree, wb_casing_count int2, wb_cas_inch int2, wb_cas_fracnum int2, wb_case_fracdenom int2, wb_cas_wt_table varchar(8), wb_casing_depth_set int4, wb_mlti_stg_tool_dpth int4, wb_amount_of_cement int4, wb_cement_measurement char(1), wb_hole_inch int2, wb_hole_frac_num int2, wb_hole_frac_denom int2, wb_top_of_cement_casing varchar(7), wb_amount_casing_left varchar(5)
wb07 (writer POSTGRES_22)
    attributes: wb_api varchar(8),BTree, wb_perf_count int2, wb_from_perf int4, wb_to_perf int4, wb_open_hole_code char(2)
wb08 (writer POSTGRES_7)
    attributes: wb_api varchar(8),BTree, wb_line_count int2, wb_lin_inch int2, wb_lin_frac_num int2, wb_lin_frac_denom int2, wb_sacks_of_cement int4, wb_top_of_liner int4, wb_bottom_of_liner int4
wb09 (writer POSTGRES_8)
    attributes: wb_api varchar(8),BTree, wb_formation_cntr int2, wb_formation_name varchar(50), wb_formation_depth int4
wb10 (writer POSTGRES_9)
    attributes: wb_api varchar(8),BTree, wb_squeeze_cntr int2, wb_squeeze_upper_depth int4, wb_squeeze_lower_depth int4, wb_squeeze_kind_amount varchar(50)
wb11 (writer POSTGRES_10)
    attributes: wb_api varchar(8),BTree, wb_fresh_water_cntr int2, wb_twdb_date date, wb_surace_casing_deter_code char(1), wb_uqwp_from int4, wb_uqwp_to int4
wb12 (writer POSTGRES_11)
    attributes: wb_api varchar(8),BTree, wb_lease_name varchar(32), wb_sec_blk_survey_loc varchar(52), wb_well_loc_miles int2, wb_well_loc_direction varchar(6), wb_well_loc_nearest_town varchar(13), wb_dist_from_survey_lines varchar(28), wb_dist_direct_near_well varchar(28)
wb13 (writer POSTGRES_12)
    attributes: wb_api varchar(8),BTree, wb_loc_county int2, wb_abstract varchar(6), wb_survey varchar(55), wb_block_number varchar(10), wb_section varchar(8), wb_alt_section varchar(4), wb_alt_abstract varchar(6), wb_feet_from_sur_sect_1 int4, wb_direc_from_ur_ect_1 varchar(13), wb_feet_from_sur_sect_2 int4, wb_direc_from_sur_sect_2 varchar(13), wb_wgs84_latitude float4, wb_wgs84_longitude float4, wb_plane_zone char(2), wb_plane_coordinate_east float4, wb_plane_coordinate_north float4, wb_verification_flag char(1)
wb14 (writer POSTGRES_13)
    attributes: wb_api varchar(8),BTree, wb_date_w3_filed date, wb_date_well_bore_plugged date, wb_plug_total_depth int4, wb_plug_cement_comp varchar(32), wb_plug_mud_filled char(1), wb_plug_mud_applied varchar(12), wb_plug_mud_weight int2, wb_plug_dril_perm_date date, wb_plug_dril_perm_no varchar(6), wb_plug_dril_comp_date date, wb_plug_log_attached char(1), wb_plug_log_released_to varchar(32), wb_plug_type_log char(1), wb_plug_fresh_water_depth int4, wb_plug_from_uwqp1 int4, wb_plug_to_uwqp1 int4, wb_plug_from_uwqp2 int4, wb_plug_to_uwqp2 int4, wb_plug_from_uwqp3 int4, wb_plug_to_uwqp3 int4, wb_plug_from_uwqp4 int4, wb_plug_to_uwqp4 int4, wb_plug_material_left char(1), wb_plug_code char(1), wb_plug_oil_dist char(2), wb_plug_oil_lse_nbr int4, wb_plug_oil_well_nbr varchar(6), wb_plug_gas_rrc_id varchar(6), wb_plug_gas_dist char(2),
      wb_plug_gas_well_no varchar(6), wb_plug_type_well char(1), wb_plug_multi_compl_flag char(1), wb_plug_cem_aff char(1), wb_plug_13a char(1), wb_plug_log_released_date date, wb_plug_log_file_rba varchar(8), wb_state_funded_plug_number int4
wb15 (writer POSTGRES_14)
    attributes: wb_api varchar(8),BTree, wb_plug_rmk_line_cnt int2, wb_plug_rmk_type_code char(1), wb_plug_remarks varchar(70)
AttributeTrimmer_2
    SRC_ATTRS = wb_nbr_of_cement_sacks
    TRIM_CHARS = "0 "
    TRIM_TO_NONE = Yes
    TRIM_TYPE = Left
    -> wb16 (writer POSTGRES_15)
wb16 (writer POSTGRES_15)
    attributes: wb_api varchar(8),BTree, wb_plug_number int2, wb_nbr_of_cement_sacks int4, wb_meas_top_of_plug int4, wb_bottom_tube_pipe_depth int4, wb_plug_calc_top int4, wb_plug_type_cement varchar(6)
AttributeTrimmer
    SRC_ATTRS = wb_plug_hole_inch,wb_plg_cas_counter
    TRIM_CHARS = "0 "
    TRIM_TO_NONE = Yes
    TRIM_TYPE = Left
    -> wb17 (writer POSTGRES_16)
wb17 (writer POSTGRES_16)
    attributes: wb_api varchar(8),BTree, wb_plg_cas_counter int2, wb_plug_cas_inch int4, wb_plug_cas_frac_num int4, wb_plug_cas_frac_denom int4, wb_plug_wgt_wgt_whole int4, wb_plug_wgt_tenths int4, wb_plug_amt_put int4, wb_plug_amt_left int4, wb_plug_hole_inch int4, wb_plug_hole_frac_num int4, wb_plug_hole_frac_denom int4
AttributeTrimmer_3
    SRC_ATTRS = wb_plug_from_perf,wb_plug_to_perf,wb_plug_perf_counter
    TRIM_CHARS = "0 "
    TRIM_TO_NONE = Yes
    TRIM_TYPE = Left
    -> wb18 (writer POSTGRES_17)
wb18 (writer POSTGRES_17)
    attributes: wb_api varchar(8),BTree, wb_plug_perf_counter int2, wb_plug_from_perf int4, wb_plug_to_perf int4, wb_plug_open_hole_indicator char(1)
wb19 (writer POSTGRES_18)
    attributes: wb_api varchar(8),BTree, wb_plug_field_no varchar(8), wb_plug_field_name varchar(32), wb_plug_oper_no varchar(6), wb_plug_oper_name varchar(32), wb_plug_lease_name varchar(32)
AttributeTrimmer_4
    SRC_ATTRS = wb_permit_number
    TRIM_CHARS = "0 "
    TRIM_TO_NONE = Yes
    TRIM_TYPE = Left
    -> wb20 (writer POSTGRES_19)
wb20 (writer POSTGRES_19)
    attributes: wb_api varchar(8),BTree, wb_permit_number int4
wb21 (writer POSTGRES_20)
    attributes: wb_api varchar(8), wb_code char(1), wb_oil_district int2, wb_oil_lse_number int4, wb_oil_well_number varchar(6), wb_gas_rrcid int4
wb22 (writer POSTGRES_21)
    attributes: wb_api varchar(8),BTree, wb_14b2_oil_code char(1), wb_14b2_oil_district int2, wb_14b2_oil_lease_number int4, wb_14b2_oil_well_number varchar(6), wb_14b2_gas_rrc_id int4, wb_14b2_application_number int4, wb_14b2_gas_district int2, wb_14b2_ext_status_flag char(1), wb_14b2_ext_cancelled_reason char(1), wb_14b2_ext_approved_date date, wb_14b2_ext_exp_date date, wb_14b2_ext_denied_date date, wb_14b2_ext_hist_date date, wb_14b2_mech_integ_viol_flag char(1), wb_14b2_plug_order_sf_hold_flag char(1), wb_14b2_pollution_viol_flag char(1), wb_14b2_field_ops_hold char(1), wb_14b2_h15_problem_flag char(1), wb_14b2_h15_not_filed_flag char(1), wb_14b2_oper_delq_flag char(1), wb_14b2_district_hold_sfp char(1), wb_14b2_dist_sf_clean_up_flag char(1), wb_14b2_dist_state_plug_flag char(1), wb_14b2_good_faith_viol_flag char(1), wb_14b2_well_other_viol_flag char(1), wb_14b2_w3c_surf_eqp_viol_flag char(1), wb_14b2_w3x_viol_flag char(1), wb_14b2_hb2259_wex_pub_ent char(1), wb_14b2_hb2259_w3x_10pct char(1),
      wb_14b2_hb2259_w3x_bonding char(1), wb_14b2_hb2259_w3x_h13_eor char(1), wb_14b2_hb2259_w3x_aop char(1), wb_14b2_hb2259_w3x_mit char(1), wb_14b2_hb2259_w3x_escrow char(1), wb_14b2_w3x_filing_key int8, wb_14b2_w3x_aop_received_date date, wb_14b2_w3x_aop_fee_rcvd_date date, wb_14b2_w3x_h15_fee_rcvd_date date, wb_14b2_w3x_escrow_funds int4, wb_14b2_60_day_letter_sent_flag char(1), wb_14b2_w1x_36_needs_bond_flag char(1), wb_14b2_w1x_36_type_coverage char(1), wb_14b2_w1x_36_amt_filed int4, wb_14b2_w1x_36_surety int4, wb_14b2_w1x_36_exp_date date, wb_14b2_12x_36_bond_number varchar(20)
DateTimeConverter
    DATETIME_ATTR = wb_h15_next_test_due_date
    OUT_FORMAT = FME
    PASSTHROUGH = YES
    REPAIR_INPUT = YES
    -> wb23 (writer POSTGRES_23)
    <REJECTED> -> wb23 (writer POSTGRES_23)
wb23 (writer POSTGRES_23)
    attributes: wb_api varchar(20),BTree, wb_h15_date_key date, wb_h15_status char(1), wb_h15_operator int4, wb_h15_next_test_due_date date, wb_h15_district int2, wb_h15_field int4, wb_h15_hist_wellbore_flag char(1), wb_h15_hist_well_ccyymmdd date, wb_h15_w1x_well char(1), wb_15_oil_gas_code char(1), wb_h15_lease_nbr int4, wb_h15_well_nbr varchar(6), wb_h15_gasid_nbr int4, wb_h15_test_date date, wb_h15_base_usable_water int4, wb_h15_type_test_flag char(1), wb_h15_top_of_fluid int4, wb_h15_fluid_test_flag char(1), wb_h15_mech_integ_test_flag char(1), wb_h15_mech_test_reason_flag char(1), wb_h15_alternate_test_period int2, wb_h15_other_mit_test_type varchar(20), wb_h15_status_date date, wb_h15_no_date_well_flag char(1), wb_h15_record_from_edi_flag char(1), wb_h15_keyed_date date, wb_h15_changed_date date, wb_h15_previous_status char(1), wb_h15_uic_test_flag char(1),
      wb_h15_2yrs_approved_flag char(1), wb_h15_mail_hold_flag char(1), wb_h15_10yr_inactive_flag char(1), wb_h15_w3x_well_flag char(1)
wb24 (writer POSTGRES_24)
    attributes: wb_api varchar(8),BTree, wb_h15_remark_key int2, wb_h15_remark_text varchar(70)
wb25 (writer POSTGRES_25)
    attributes: wb_api varchar(8),BTree, wb_sb126_designation_flag char(1), wb_sb126_desig_effective_date date, wb_sb126_desig_revised_date date, wb_sb126_desig_letter_date date, wb_sb126_cert_effect_date date, wb_sb126_cert_revoked_date date, wb_sb126_cert_denial_date date, wb_sb126_denial_reason_flag char(1)
wb26 (writer POSTGRES_26)
    attributes: wb_api varchar(8),BTree, wb_dastat_stat_num int4, wb_dastat_uniq_num int2, wb_dastat_deleted_flag char(1)
wb27 (writer POSTGRES_27)
    attributes: wb_api varchar(8),BTree, wb_w3c_1yr_flag char(1), wb_w3c_1yr_filed_date date, wb_w3c_1yr_filing_oper int4, wb_w3c_5yr_flag char(1), wb_w3c_5yr_filed_date date, wb_w3c_5yr_filing_oper int4, wb_w3c_10yr_flag char(1), wb_w3c_10yr_filed_date date, wb_w3c_10yr_filing_oper int4, wb_w3c_14b2_removal_date date, wb_w3c_extension_flag char(1), wb_w3c_extension_date date, wb_w3c_5yr_flag_previous char(1), wb_w3c_10yr_flag_previous char(1)
wb01 (writer POSTGRES_1)
    attributes: wb_api varchar(8),BTree, wb_orig_compl_date date, wb_nxt_avail_suffix varchar(2), wb_nxt_avail_hole_chge_nbr varchar(2), wb_field_district varchar(2), wb_res_cnty_code varchar(3), wb_orig_cmpl_cc char(1), wb_total_depth int4, wb_valid_fluid_level int4, wb_certification_revoked_date date, wb_certification_denial_date date, wb_denial_reason_flag char(1), wb_error_api_assign_code char(1), wb_refer_correct_api_nbr varchar(8), wb_dummy_api_number varchar(8), wb_date_dummy_replaced varchar(8), wb_newest_drl_pmt_nbr varchar(8), wb_cancel_expire_code char(1), wb_except_13_a char(1), wb_fresh_water_flag char(1), wb_plug_flag char(1), wb_previous_api_nbr varchar(8), wb_completion_data_ind char(1), wb_hist_date_source_flag char(1), wb_ex14b2_count int2, wb_designation_hb_1975_flag char(1), wb_designation_effective_date date, wb_designation_revised_date date, wb_designation_letter_date date, wb_certification_effect_date date,
      wb_water_land_code char(1), wb_total_bonded_depth int4, wb_override_est_plug_cost int4, wb_shut_in_date date, wb_override_bonded_depth int2, wb_subj_to_14b2_flag char(1), wb_pend_removal_14b2_flag char(1), wb_orphan_well_hold_flag char(1), wb_w3x_well_flag char(1)

Bookmark: WB02 - Completion Infrmation
CSV (reader CSV2_1)
    attributes: wb_api string, wb_og_code string, wb_oil_dist string, wb_oil_lse_nbr string, wb_oil_well_nbr string, wb_gas_rrc string, wb_gas_dist string, wb_gas_well_no string, wb_multi_well_rec_nbr string, wb_api_suffix string, wb_active_inactive_code string, wb_dwn_hole_commingle_code string, wb_created_from_pi_flag string, wb_rule_37_nbr string, wb_p_15 string, wb_p_12 string, wb_plug_date_ptr string
    -> wb02 (writer POSTGRES_2)

Bookmark: WB03 - Technical Data Forms File Date
CSV (reader CSV2_2)
    attributes: wb_api string, wb_file_key string, wb_file_date string, wb_except_rule_11 string, wb_cement_affidavit string, wb_g_5 string, wb_w_12 string, wb_dir_survey string, wb_w2_g1_date string, wb_compl_date string, wb_drl_compl_date string, wb_plugb_depth1 string, wb_plugb_depth2 string, wb_water_injection_nbr string, wb_salt_wtr string, wb_remarks string, wb_elevation string, wb_elevation_code string, wb_log_file_rba string, wb_docket_nbr string, wb_psa_well_flag string, wb_allocation_well_flag string
    -> wb03 (writer POSTGRES_3)

Bookmark: WB04 - Remarks Segment
CSV (reader CSV2_3)
    attributes: wb_api string, wb_rmk_line_cnt string, wb_rmk_type_code string, wb_remarks string
    -> wb04 (writer POSTGRES_4)

Bookmark: WB05 - Tubing
CSV (reader CSV2_4)
    attributes: wb_api string, wb_segment_counter string, wb_tubing_inches string, wb_tubing_numerator string, wb_tubing_denominator string, wb_depth_set string, wb_packer_set string
    -> wb05 (writer POSTGRES_5)

Bookmark: WB06 - Casing
CSV (reader CSV2_5)
    attributes: wb_api string, wb_casing_count string, wb_cas_inch string, wb_cas_fracnum string, wb_case_fracdenom string, wb_cas_wt_table string, wb_casing_depth_set string, wb_mlti_stg_tool_dpth string, wb_amount_of_cement string, wb_cement_measurement string, wb_hole_inch string, wb_hole_frac_num string, wb_hole_frac_denom string, wb_top_of_cement_casing string, wb_amount_casing_left string
    -> wb06 (writer POSTGRES_6)

Bookmark: WB07 - Perfs
CSV (reader CSV2_6)
    attributes: wb_api string, wb_perf_count string, wb_from_perf string, wb_to_perf string, wb_open_hole_code string
    -> wb07 (writer POSTGRES_22)

Bookmark: WB08 - Liners
CSV (reader CSV2_7)
    attributes: wb_api string, wb_line_count string, wb_lin_inch string, wb_lin_frac_num string, wb_lin_frac_denom string, wb_sacks_of_cement string, wb_top_of_liner string, wb_bottom_of_liner string
    -> wb08 (writer POSTGRES_7)

Bookmark: WB09 - Formation
CSV (reader CSV2_8)
    attributes: wb_api string, wb_formation_cntr string, wb_formation_name string, wb_formation_depth string
    -> wb09 (writer POSTGRES_8)

Bookmark: WB10 - Squeezes
CSV (reader CSV2_9)
    attributes: wb_api string, wb_squeeze_cntr string, wb_squeeze_upper_depth string, wb_squeeze_lower_depth string, wb_squeeze_kind_amount string
    -> wb10 (writer POSTGRES_9)

Bookmark: WB11 - Usable Water Qlty
CSV (reader CSV2_10)
    attributes: wb_api string, wb_fresh_water_cntr string, wb_twdb_date string, wb_surace_casing_deter_code string, wb_uqwp_from string, wb_uqwp_to string
    -> wb11 (writer POSTGRES_10)

Bookmark: WB12 - Old Location Segment
CSV (reader CSV2_11)
    attributes: wb_api string, wb_lease_name string, wb_sec_blk_survey_loc string, wb_well_loc_miles string, wb_well_loc_direction string, wb_well_loc_nearest_town string, wb_dist_from_survey_lines string, wb_dist_direct_near_well string
    -> wb12 (writer POSTGRES_11)

Bookmark: WB13 - New Location Segment
CSV (reader CSV2_12)
    attributes: wb_api string, wb_loc_county string, wb_abstract string, wb_survey string, wb_block_number string, wb_section string, wb_alt_section string, wb_alt_abstract string, wb_feet_from_sur_sect_1 string, wb_direc_from_ur_ect_1 string, wb_feet_from_sur_sect_2 string, wb_direc_from_sur_sect_2 string, wb_wgs84_latitude string, wb_wgs84_longitude string, wb_plane_zone string, wb_plane_coordinate_east string, wb_plane_coordinate_north string, wb_verification_flag string
    -> wb13 (writer POSTGRES_12)

Bookmark: WB14 - Plugging Data Segment
CSV (reader CSV2_13)
    attributes: wb_api string, wb_date_w3_filed string, wb_date_well_bore_plugged string, wb_plug_total_depth string, wb_plug_cement_comp string, wb_plug_mud_filled string, wb_plug_mud_applied string, wb_plug_mud_weight string, wb_plug_dril_perm_date string, wb_plug_dril_perm_no string, wb_plug_dril_comp_date string, wb_plug_log_attached string, wb_plug_log_released_to string, wb_plug_type_log string, wb_plug_fresh_water_depth string, wb_plug_from_uwqp1 string, wb_plug_to_uwqp1 string, wb_plug_from_uwqp2 string, wb_plug_to_uwqp2 string, wb_plug_from_uwqp3 string, wb_plug_to_uwqp3 string, wb_plug_from_uwqp4 string, wb_plug_to_uwqp4 string, wb_plug_material_left string, wb_plug_code string, wb_plug_oil_dist string, wb_plug_oil_lse_nbr string, wb_plug_oil_well_nbr string, wb_plug_gas_rrc_id string, wb_plug_gas_dist string,
      wb_plug_gas_well_no string, wb_plug_type_well string, wb_plug_multi_compl_flag string, wb_plug_cem_aff string, wb_plug_13a string, wb_plug_log_released_date string, wb_plug_log_file_rba string, wb_state_funded_plug_number string
    -> wb14 (writer POSTGRES_13)

Bookmark: WB15 - Plug Remarks Segment
CSV (reader CSV2_14)
    attributes: wb_api string, wb_plug_rmk_line_cnt string, wb_plug_rmk_type_code string, wb_plug_remarks string
    -> wb15 (writer POSTGRES_14)

Bookmark: WB16 - Plugging record segment
CSV (reader CSV2_15)
    attributes: wb_api string, wb_plug_number string, wb_nbr_of_cement_sacks string, wb_meas_top_of_plug string, wb_bottom_tube_pipe_depth string, wb_plug_calc_top string, wb_plug_type_cement string
    -> AttributeTrimmer_2

Bookmark: WB17 - Plugging Liner and Tubing Segment
CSV (reader CSV2_16)
    attributes: wb_api string, wb_plg_cas_counter string, wb_plug_cas_inch string, wb_plug_cas_frac_num string, wb_plug_cas_frac_denom string, wb_plug_wgt_wgt_whole string, wb_plug_wgt_tenths string, wb_plug_amt_put string, wb_plug_amt_left string, wb_plug_hole_inch string, wb_plug_hole_frac_num string, wb_plug_hole_frac_denom string
    -> AttributeTrimmer

Bookmark: WB18 - Plugging perfs record
CSV (reader CSV2_17)
    attributes: wb_api string, wb_plug_perf_counter string, wb_plug_from_perf string, wb_plug_to_perf string, wb_plug_open_hole_indicator string
    -> AttributeTrimmer_3

Bookmark: WB19 - Plugging Nomenclature name
CSV (reader CSV2_18)
    attributes: wb_api string, wb_plug_field_no string, wb_plug_field_name string, wb_plug_oper_no string, wb_plug_oper_name string, wb_plug_lease_name string
    -> wb19 (writer POSTGRES_18)

Bookmark: WB20 - Drilling Permint Number
CSV (reader CSV2_19)
    attributes: wb_api string, wb_permit_number string
    -> AttributeTrimmer_4

Bookmark: WB21 - Well ID Segment
CSV (reader CSV2_20)
    attributes: wb_api string, wb_code string, wb_oil_district string, wb_oil_lse_number string, wb_oil_well_number string, wb_gas_rrcid string
    -> wb21 (writer POSTGRES_20)

Bookmark: WB22 - 14(B)(2) Extension Sytem
CSV (reader CSV2_21)
    attributes: wb_api string, wb_14b2_oil_code string, wb_14b2_oil_district string, wb_14b2_oil_lease_number string, wb_14b2_oil_well_number string, wb_14b2_gas_rrc_id string, wb_14b2_application_number string, wb_14b2_gas_district string, wb_14b2_ext_status_flag string, wb_14b2_ext_cancelled_reason string, wb_14b2_ext_approved_date string, wb_14b2_ext_exp_date string, wb_14b2_ext_denied_date string, wb_14b2_ext_hist_date string, wb_14b2_mech_integ_viol_flag string, wb_14b2_plug_order_sf_hold_flag string, wb_14b2_pollution_viol_flag string, wb_14b2_field_ops_hold string, wb_14b2_h15_problem_flag string, wb_14b2_h15_not_filed_flag string, wb_14b2_oper_delq_flag string, wb_14b2_district_hold_sfp string, wb_14b2_dist_sf_clean_up_flag string, wb_14b2_dist_state_plug_flag string, wb_14b2_good_faith_viol_flag string, wb_14b2_well_other_viol_flag string, wb_14b2_w3c_surf_eqp_viol_flag string, wb_14b2_w3x_viol_flag string, wb_14b2_hb2259_wex_pub_ent string, wb_14b2_hb2259_w3x_10pct string,
      wb_14b2_hb2259_w3x_bonding string, wb_14b2_hb2259_w3x_h13_eor string, wb_14b2_hb2259_w3x_aop string, wb_14b2_hb2259_w3x_mit string, wb_14b2_hb2259_w3x_escrow string, wb_14b2_w3x_filing_key string, wb_14b2_w3x_aop_received_date string, wb_14b2_w3x_aop_fee_rcvd_date string, wb_14b2_w3x_h15_fee_rcvd_date string, wb_14b2_w3x_escrow_funds string, wb_14b2_60_day_letter_sent_flag string, wb_14b2_w1x_36_needs_bond_flag string, wb_14b2_w1x_36_type_coverage string, wb_14b2_w1x_36_amt_filed string, wb_14b2_w1x_36_surety string, wb_14b2_w1x_36_exp_date string, wb_14b2_12x_36_bond_number string
    -> wb22 (writer POSTGRES_21)

Bookmark: WB23 - H15 Segment
CSV (reader CSV2_22)
    attributes: wb_api string, wb_h15_date_key string, wb_h15_status string, wb_h15_operator string, wb_h15_next_test_due_date string, wb_h15_district string, wb_h15_field string, wb_h15_hist_wellbore_flag string, wb_h15_hist_well_ccyymmdd string, wb_h15_w1x_well string, wb_15_oil_gas_code string, wb_h15_lease_nbr string, wb_h15_well_nbr string, wb_h15_gasid_nbr string, wb_h15_test_date string, wb_h15_base_usable_water string, wb_h15_type_test_flag string, wb_h15_top_of_fluid string, wb_h15_fluid_test_flag string, wb_h15_mech_integ_test_flag string, wb_h15_mech_test_reason_flag string, wb_h15_alternate_test_period string, wb_h15_other_mit_test_type string, wb_h15_status_date string, wb_h15_no_date_well_flag string, wb_h15_record_from_edi_flag string, wb_h15_keyed_date string, wb_h15_changed_date string, wb_h15_previous_status string, wb_h15_uic_test_flag string,
      wb_h15_2yrs_approved_flag string, wb_h15_mail_hold_flag string, wb_h15_10yr_inactive_flag string, wb_h15_w3x_well_flag string
    -> DateTimeConverter

Bookmark: WB24 - WBH15 Remarks
CSV (reader CSV2_23)
    attributes: wb_api string, wb_h15_remark_key string, wb_h15_remark_text string
    -> wb24 (writer POSTGRES_24)

Bookmark: WB25 - Senate Bill 126
CSV (reader CSV2_24)
    attributes: wb_api string, wb_sb126_designation_flag string, wb_sb126_desig_effective_date string, wb_sb126_desig_revised_date string, wb_sb126_desig_letter_date string, wb_sb126_cert_effect_date string, wb_sb126_cert_revoked_date string, wb_sb126_cert_denial_date string, wb_sb126_denial_reason_flag string
    -> wb25 (writer POSTGRES_25)

Bookmark: WB26 - Drilling Permit Status Number
CSV (reader CSV2_25)
    attributes: wb_api string, wb_dastat_stat_num string, wb_dastat_uniq_num string, wb_dastat_deleted_flag string
    -> wb26 (writer POSTGRES_26)

Bookmark: WB27 - W3C Segment
CSV (reader CSV2_26)
    attributes: wb_api string, wb_w3c_1yr_flag string, wb_w3c_1yr_filed_date string, wb_w3c_1yr_filing_oper string, wb_w3c_5yr_flag string, wb_w3c_5yr_filed_date string, wb_w3c_5yr_filing_oper string, wb_w3c_10yr_flag string, wb_w3c_10yr_filed_date string, wb_w3c_10yr_filing_oper string, wb_w3c_14b2_removal_date string, wb_w3c_extension_flag string, wb_w3c_extension_date string, wb_w3c_5yr_flag_previous string, wb_w3c_10yr_flag_previous string
    -> wb27 (writer POSTGRES_27)

Bookmark: WB01 - Technical Root
CSV (reader CSV2_27)
    attributes: wb_api string, wb_nxt_avail_suffix string, wb_nxt_avail_hole_chge_nbr string, wb_field_district string, wb_res_cnty_code string, wb_orig_cmpl_cc string, wb_orig_compl_date string, wb_total_depth string, wb_valid_fluid_level string, wb_certification_revoked_date string, wb_certification_denial_date string, wb_denial_reason_flag string, wb_error_api_assign_code string, wb_refer_correct_api_nbr string, wb_dummy_api_number string, wb_date_dummy_replaced string, wb_newest_drl_pmt_nbr string, wb_cancel_expire_code string, wb_except_13_a string, wb_fresh_water_flag string, wb_plug_flag string, wb_previous_api_nbr string, wb_completion_data_ind string, wb_hist_date_source_flag string, wb_ex14b2_count string, wb_designation_hb_1975_flag string, wb_designation_effective_date string, wb_designation_revised_date string, wb_designation_letter_date string, wb_certification_effect_date string,
      wb_water_land_code string, wb_total_bonded_depth string, wb_override_est_plug_cost string, wb_shut_in_date string, wb_override_bonded_depth string, wb_subj_to_14b2_flag string, wb_pend_removal_14b2_flag string, wb_orphan_well_hold_flag string, wb_w3x_well_flag string
    -> wb01 (writer POSTGRES_1)
