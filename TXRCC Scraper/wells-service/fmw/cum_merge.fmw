FME workspace cum_merge.fmw

Parameters:
- DestDataset_POSTGIS = pg.whitestar.com   # Connection
- SourceDataset_POSTGIS_7 = pg.whitestar.com   # Connection
- SourceDataset_POSTGIS_8 = pg.whitestar.com   # Connection

Readers:
- POSTGIS_1: POSTGIS from $(SourceDataset_POSTGIS_7)
- POSTGIS_2: POSTGIS from $(SourceDataset_POSTGIS_8)

Writers:
- POSTGIS_3: POSTGIS to $(DestDataset_POSTGIS)

tx_pipelines_for_wells (reader POSTGIS_1)
    attributes: tpms_id int4, oper_link int4, ops_id int4, p5_num varchar(6), oper_nm varchar(40), sys_nm varchar(40), subsys_nm varchar(40), t4permit varchar(5), diameter float4, commodity1 varchar(3), commodity2 varchar(3), commodity3 varchar(3), cmdty_desc varchar(40), interstate varchar(1), status_cd varchar(1), quality_cd varchar(1), systype varchar(1), county varchar(3), com_carrie varchar(1), pline_id varchar(20), sys_id varchar(6), npms_sys_i int4, albers_mil float8, length float8
    -> Tester_2
Tester_2
    BOOL_OP = OR
    COMPOSITE_TEST = 1 OR 2 OR 3 OR 4
    TEST_CLAUSE:
      TEST @Value(systype) = G
      TEST @Value(systype) = T
      TEST @Value(systype) = L
      TEST @Value(systype) = O
    TEST_MODE = TEST
    PASSED -> EsriReprojector_2
EsriReprojector_2
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> TestFilter_2
    REPROJECTED -> TestFilter_4
    REPROJECTED -> TestFilter_6
tx_header_pre_cum (reader POSTGIS_2)
    attributes: wstar_id varchar(14),BTree, api varchar(8),BTree, api_state int2,BTree, api_cnty int2,BTree, state varchar(2),BTree, county varchar(25),BTree, srf_lat float8, srf_lng float8, bot_lat float8, bot_lng float8, rrdist varchar(3), post_code varchar(10), oil_lease varchar(12), gas_lease varchar(8), elev_gl int2, elev_kb int2, elev_df int2, elev_ca int2, well_name varchar(50), well_num varchar(6), operator varchar(50), field_nam varchar(50), well_type varchar(12), abs_num varchar(12), block_nam varchar(50), survey_num varchar(8), survey_nam text, srv_nam2 text, scr_fileno varchar(10), loc_desc text,
      miles_town float8, dir_town varchar(6), near_town varchar(14), dis_srvln varchar(50), dis_nwell varchar(50), wellb_abs varchar(6), wellb_srv text, wellb_blk varchar(10), wellb_sec varchar(8), wb_altsec varchar(6), wb_altabs varchar(6), ftg_src varchar(5), footage_1 int4, ftg1_dir varchar(14), footage_2 int4, ftg2_dir varchar(14), quad_name varchar(50), quad_code varchar(10), freshwater varchar(1), radioactv varchar(1), permit_num int4, prmt_date date, spud_date date, comp_date date, plug_date date, tot_depth int4, acres int4, bhdata1 varchar(6), oglease varchar(12), cum_oil float8,
      cum_gas float8, cum_cond int4, cum_csgd float8, nwells int4, nmon_oil int2, nmon_gas int2, nmon_cond int2, nmon_csgd int2, tpms_id int4, sys_nm varchar(50), systype varchar(1), diameter float4, commodity1 varchar(3), interstate varchar(1), status_cd varchar(1), dist_pipe int2, data_src varchar(5), surface_id int4,BTree, updt_date date,BTree
    -> FeatureJoiner [LEFT]
SQLCreator
    DATASET = pg.whitestar.com
    EXPOSED_ATTRIBUTE_LIST = cum_cond,cum_csgd,cum_gas,cum_oil,lease_no,nmon_cond,nmon_csgd,nmon_gas,nmon_oil
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT = select * from cum_og
    RESULT -> FeatureJoiner [RIGHT]
    RESULT -> FeatureJoiner_2 [RIGHT]
FeatureJoiner
    ATTR_CONFLICT_RES = Use Right
    GEOMETRY_HANDLING = Use Left
    JOIN_KEYS = oil_lease lease_no STRING
    JOIN_MODE = Inner
    JOINED -> Junction_2
    UNJOINED_LEFT -> AttributeCreator
    <REJECTED> -> Junction_2
AttributeCreator
    ATTR_TABLE = SET_TO lease_no = FME_NULL_VALUE
    -> Junction_2
Junction_2
    -> FeatureJoiner_2 [LEFT]
FeatureJoiner_2
    ATTR_CONFLICT_RES = Use Right
    GEOMETRY_HANDLING = Use Left
    JOIN_KEYS = gas_lease lease_no STRING
    JOIN_MODE = Inner
    JOINED -> Junction_3
    UNJOINED_LEFT -> Junction_3
    <REJECTED> -> Junction_3
Junction_3
    -> FeatureMerger_3 [REQUESTOR]
    -> Tester
Tester
    BOOL_OP = OR
    COMPOSITE_TEST = 1 OR 2 OR 3 OR 4
    TEST_CLAUSE:
      TEST @Value(post_code) = GAS
      TEST @Value(post_code) = O&G
      TEST @Value(post_code) = OIL
      TEST @Value(post_code) = LOC
    TEST_MODE = TEST
    PASSED -> EsriReprojector
EsriReprojector
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> TestFilter
    REPROJECTED -> TestFilter_3
    REPROJECTED -> TestFilter_5
EsriReprojector_3
    DEST = ESRIWKT|GCS_North_American_1927|GEOGCS["GCS_North_American_1927",DATUM["D_North_American_1927",SPHEROID["Clarke_1866",6378206.4,294.9786982]],PRIMEM["Greenwich",0.0],UNIT["Degree",0.0174532925199433]]
    GEOTRANSFORMATION_DIRECTION = Forward
    INTERPOLATION_TYPE_NAME = Nearest Neighbor
    RASTER_CELL_SIZE = Preserve Cells
    RASTER_TOLERANCE = 0.0
    SOURCE = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    REPROJECTED -> AttributeRenamer
AttributeRenamer
    ATTR_TABLE = RENAME_SET_DEFAULT _distance > dist_pipe
    -> AttributeRounder
AttributeRounder
    PLACES = 0
    ROUND_TYPE = Nearest
    SRC_ATTRS = dist_pipe
    -> FeatureMerger_3 [SUPPLIER]
FeatureMerger_3
    ATTR_ACCUM_MODE = Merge Supplier
    ATTR_CONFLICT_RES = Use Supplier
    IGNORE_NULLS = No
    JOIN_KEYS = @Value(wstar_id) @Value(wstar_id) AUTO
    MERGE_TYPE = Attributes Only
    PROCESS_DUPS = NO
    REJECT_NULL_MISSING_KEYS = No
    SUPPLIERS_FIRST = No
    MERGED -> Junction
    UNMERGED_REQUESTOR -> Junction
Junction
    -> StringLengthCalculator_3
AttributeCreator_2
    ATTR_TABLE = SET_TO api = @Value(wstar_id)
    -> Sorter
Sorter
    SORT_PARM = api ALPHA ASCENDING
    SORTED -> tx_header_latest_build (writer POSTGIS_3)
tx_header_latest_build (writer POSTGIS_3)
    attributes: wstar_id varchar(14),BTree, api varchar(14),BTree, api_state int2, api_cnty int2,BTree, state varchar(2), county varchar(25),BTree, srf_lat float8, srf_lng float8, bot_lat float8, bot_lng float8, rrdist varchar(3), post_code varchar(10), oil_lease varchar(12), gas_lease varchar(8), elev_gl int2, elev_kb int2, elev_df int2, elev_ca int2, well_name varchar(50), well_num varchar(6), operator varchar(50), field_nam varchar(50), well_type varchar(12), abs_num varchar(12), block_nam varchar(32), survey_num varchar(8), survey_nam text, srv_nam2 text, scr_fileno varchar(10), loc_desc text,
      miles_town float8, dir_town varchar(6), near_town varchar(14), dis_srvln varchar(50), dis_nwell varchar(50), wellb_abs varchar(6), wellb_srv text, wellb_blk varchar(10), wellb_sec varchar(8), wb_altsec varchar(6), wb_altabs varchar(6), ftg_src varchar(5), footage_1 varchar(20), ftg1_dir varchar(14), footage_2 int4, ftg2_dir varchar(14), quad_name varchar(50), quad_code varchar(10), freshwater varchar(1), radioactv varchar(1), permit_num int4, prmt_date date, spud_date date, comp_date date, plug_date date, tot_depth int4, acres int4, bhdata1 varchar(6), oglease varchar(12), cum_oil float8,
      cum_gas float8, cum_cond int4, cum_csgd float8, nwells int4, nmon_oil int2, nmon_gas int2, nmon_cond int2, nmon_csgd int2, tpms_id int4, sys_nm varchar(50), systype char(1), diameter float4, commodity1 char(3), interstate char(1), status_cd char(1), dist_pipe int2, data_src varchar(5), surface_id int4,BTree, updt_date date,BTree

Bookmark: GAS
TestFilter_2
    DEFAULT_VALUE = <UNFILTERED>
    TEST_LIST:
      "BOOL_OP,OR,COMPOSITE_TEST,""""""1 OR 2"""""",TEST_CLAUSE,TEST @Value(systype) = G
      TEST @Value(systype) = T",GAS
    GAS -> NeighborFinder [CANDIDATE]
TestFilter
    DEFAULT_VALUE = <UNFILTERED>
    TEST_LIST = "BOOL_OP,OR,COMPOSITE_TEST,""""""1"""""",TEST_CLAUSE,TEST @Value(post_code) = GAS",GAS
    GAS -> NeighborFinder [BASE]
NeighborFinder
    ATTR_ACCUM_MODE = Merge Candidate
    ATTR_CONFLICT_RES = Use Base
    CANDIDATES_FIRST = No
    INSERT_VERTEX = No
    K = 1
    MAX = 5280
    MEASURES_FROM_CANDIDATE = Yes
    MEASURE_TYPE = Continuous
    MODE = Bases and Candidates
    TREAT_POLYGON_AS = Lines
    MATCHED -> EsriReprojector_3

Bookmark: OIL
TestFilter_4
    DEFAULT_VALUE = <UNFILTERED>
    TEST_LIST:
      "BOOL_OP,OR,COMPOSITE_TEST,""""""1 OR 2"""""",TEST_CLAUSE,TEST @Value(systype) = L
      TEST @Value(systype) = O",OIL
    OIL -> NeighborFinder_2 [CANDIDATE]
TestFilter_3
    DEFAULT_VALUE = <UNFILTERED>
    TEST_LIST = "BOOL_OP,OR,COMPOSITE_TEST,""""""1"""""",TEST_CLAUSE,TEST @Value(post_code) = OIL",OIL
    OIL -> NeighborFinder_2 [BASE]
NeighborFinder_2
    ATTR_ACCUM_MODE = Merge Candidate
    ATTR_CONFLICT_RES = Use Base
    CANDIDATES_FIRST = No
    INSERT_VERTEX = No
    K = 1
    MAX = 5280
    MEASURES_FROM_CANDIDATE = Yes
    MEASURE_TYPE = Continuous
    MODE = Bases and Candidates
    TREAT_POLYGON_AS = Lines
    MATCHED -> EsriReprojector_3

Bookmark: O&G or LOC
TestFilter_6
    DEFAULT_VALUE = <UNFILTERED>
    TEST_LIST:
      "BOOL_OP,OR,COMPOSITE_TEST,""""""1 OR 2 OR 3 OR 4"""""",TEST_CLAUSE,TEST @Value(systype) = G
      TEST @Value(systype) = T
      TEST @Value(systype) = L
      TEST @Value(systype) = O",O&G
    O&G -> NeighborFinder_3 [CANDIDATE]
TestFilter_5
    DEFAULT_VALUE = <UNFILTERED>
    TEST_LIST:
      "BOOL_OP,OR,COMPOSITE_TEST,""""""1 OR 2"""""",TEST_CLAUSE,TEST @Value(post_code) = O&G
      TEST @Value(post_code) = LOC",O&G
    O&G -> NeighborFinder_3 [BASE]
NeighborFinder_3
    ATTR_ACCUM_MODE = Merge Candidate
    ATTR_CONFLICT_RES = Use Base
    CANDIDATES_FIRST = No
    INSERT_VERTEX = No
    K = 1
    MAX = 5280
    MEASURES_FROM_CANDIDATE = Yes
    MEASURE_TYPE = Continuous
    MODE = Bases and Candidates
    TREAT_POLYGON_AS = Lines
    MATCHED -> EsriReprojector_3

Bookmark: wstar_id Check/Correct
StringLengthCalculator_3
    LENGTH_ATTR = _length_wstar_id
    SRC_ATTR = wstar_id
    -> Tester_4
Tester_4
    BOOL_OP = OR
    COMPOSITE_TEST = 1
    TEST_CLAUSE = TEST @Value(_length_wstar_id) < 14
    TEST_MODE = TEST
    PASSED -> StringPadder_3
    FAILED -> AttributeCreator_2
StringPadder_3
    BLANK_ATTRIBUTE = Yes
    PADCHAR = 0
    SIDE = Right
    SRC_ATTRS = wstar_id
    WIDTH = 14
    -> AttributeCreator_2
    <REJECTED> -> AttributeCreator_2
