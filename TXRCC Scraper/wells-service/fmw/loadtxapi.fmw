FME workspace loadtxapi.fmw

Parameters:
- SourceDataset_DBF =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   # Source dBASE (DBF) File(s)
- FEATURE_TYPES =
- DestDataset_POSTGRES = pg.whitestar.com   # Connection

Readers:
- DBF_1: DBF from $(SourceDataset_DBF)

Writers:
- POSTGRES_1: POSTGRES to $(DestDataset_POSTGRES)

api001 (reader DBF_1)
    attributes: ABSTRACT char(6), APINUM char(8), BLOCK char(10), COMPLETION char(8), FIELD_NAME char(32), LEASE_NAME char(32), GAS_RRCID char(6), OIL_GAS_CO char(1), ON_OFF_SCH char(1), OPERATOR char(32), PERMIT_NUM char(6), PLUG_DATE char(8), REFER_TO_A char(8), SECTION char(8), SURVEY char(55), TOTAL_DEPT char(5), WELLID char(6), QUADNUM char(7), OBJECTID_1 long
    -> BulkAttributeRenamer
BulkAttributeRenamer
    ATTRCHOICE = All Attributes
    CASE_CHANGE_TYPE = lower
    MODE_CHOICE = RENAME
    PATTERN_ACTION_DISP = CASECHANGE
    -> AttributeTrimmer
AttributeTrimmer
    SRC_ATTRS = plug_date,completion
    TRIM_CHARS = " "
    TRIM_TO_NONE = Yes
    TRIM_TYPE = Both
    -> Tester
AttributeRenamer
    ATTR_TABLE = RENAME_SET_DEFAULT completion > completion_date
    -> Tester_2
txapi (writer POSTGRES_1)
    attributes: apinum varchar(8),BTree, abstract varchar(6), block varchar(10), completion_date date, field_name varchar(32), lease_name varchar(32), gas_rrcid varchar(6), oil_gas_co varchar(1), on_off_sch varchar(1), operator varchar(32), permit_num varchar(6), plug_date varchar(8), refer_to_a varchar(8), section varchar(8), survey varchar(55), total_dept varchar(5), wellid varchar(6), quadnum varchar(7)

Bookmark: Manage Completion Date
Tester
    BOOL_OP = OR
    COMPOSITE_TEST = 1 OR 2
    TEST_CLAUSE:
      TEST @Value(completion) = 0
      TEST @Value(completion) = ""
    TEST_MODE = TEST
    PASSED -> AttributeCreator
    FAILED -> DateTimeConverter
AttributeCreator
    ATTR_TABLE = SET_TO completion
    -> DateTimeConverter
DateTimeConverter
    DATETIME_ATTR = completion
    OUT_FORMAT = FME
    PASSTHROUGH = YES
    REPAIR_INPUT = YES
    -> AttributeRenamer
    <REJECTED> -> AttributeRenamer

Bookmark: Manage Plug Date
Tester_2
    BOOL_OP = OR
    COMPOSITE_TEST = 1 OR 2
    TEST_CLAUSE:
      TEST @Value(plug_date) = 0
      TEST @Value(plug_date) = ""
    TEST_MODE = TEST
    PASSED -> AttributeCreator_2
    FAILED -> DateTimeConverter_2
AttributeCreator_2
    ATTR_TABLE = SET_TO plug_date
    -> DateTimeConverter_2
DateTimeConverter_2
    DATETIME_ATTR = plug_date
    OUT_FORMAT = FME
    PASSTHROUGH = NO
    REPAIR_INPUT = YES
    -> txapi (writer POSTGRES_1)
    <REJECTED> -> txapi (writer POSTGRES_1)
