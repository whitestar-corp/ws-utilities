FME workspace well_dem_intersector_and_preprocessor.fmw

Parameters:
- SourceDataset_POSTGIS = pg.whitestar.com   # Connection
- DestDataset_POSTGIS = pg.whitestar.com   # Connection

Readers:
- GEODATABASE_SDE_RASTER_DATASET_1: GEODATABASE_SDE_RASTER_DATASET
- POSTGIS_1: POSTGIS from $(SourceDataset_POSTGIS)

Writers:
- POSTGIS_2: POSTGIS to $(DestDataset_POSTGIS)

well_s (reader POSTGIS_1)
    attributes: surface_id int4, symnum int4, api varchar(8), reliab varchar(2), long27 float8, lat27 float8, long83 float8, lat83 float8, wellid varchar(5)
    -> StringLengthCalculator
Junction_8
    -> DatabaseJoiner

Bookmark: Calculate wstar_id and 10 digiti API Numbers. api and wstar_id are based on wellid if no API number present. 42 + county code + 5 + 08d format wellid
StringLengthCalculator
    LENGTH_ATTR = _length
    SRC_ATTR = api
    -> TestFilter_4
TestFilter_4
    DEFAULT_VALUE = <UNFILTERED>
    TEST_LIST = "BOOL_OP,OR,COMPOSITE_TEST,""""""1"""""",TEST_CLAUSE,TEST @Value(_length) = 8",8,"BOOL_OP,OR,COMPOSITE_TEST,""""""1"""""",TEST_CLAUSE,TEST @Value(_length) = 3",3
    8 -> StringConcatenator
    3 -> StringFormatter
    <UNFILTERED> -> Junction_8
StringConcatenator
    ACTION = Create New Attribute
    PARM_LINE = fme_basicstring:2%11%4:42@Value(api)0000
    VAL_ATTR = wstar_id
    -> Junction_8
Note: Create 'API' based on 5 + 08d wellid
StringFormatter
    FORMAT = 08d
    SRC_ATTRS = surface_id
    -> StringConcatenator_2
StringConcatenator_2
    ACTION = Create New Attribute
    PARM_LINE = fme_basicstring:2%11%1%18:42@Value(api)5@Value(surface_id)
    VAL_ATTR = wstar_id
    -> Junction_8

Bookmark: Calculate elevations
DatabaseJoiner
    ADDED_FIELDS = elev_ca
    ATTR_ACCUM_MODE = Prefix Joined
    CACHE_SIZE = 20000
    DATASET = pg.whitestar.com
    FORMAT = POSTGIS
    JOINED_ATTRIBUTE_PREFIX = known
    JOIN_KEYS = wstar_id wstar_id
    MATCH_MULTIPLE_DISPLAY = Create a feature for each match
    MATCH_RULE_DISPLAY = Match All (1:M)
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    PREFETCH_EXHAUSTIVE = Yes
    PREFETCH_QUERY = select wstar_id, elev_ca from tx_header
    TABLE = public.tx_header
    JOINED -> AttributeRenamer
    UNJOINED -> PointOnRasterValueExtractor_2 [POINT]
AttributeRenamer
    ATTR_TABLE = RENAME_SET_DEFAULT known_elev_ca > elev_ca
    -> Junction
TEXAS_CLIP_LL27 (reader GEODATABASE_SDE_RASTER_DATASET_1)
    -> PointOnRasterValueExtractor_2 [RASTER]
PointOnRasterValueExtractor_2
    INTERPOLATION_TYPE_NAME = Nearest Neighbor
    POINT -> AttributeRenamer_8
AttributeRenamer_8
    ATTR_TABLE = RENAME_SET_DEFAULT _band{0}.value > elev_ca
    -> AttributeRounder
AttributeRounder
    PLACES = 0
    ROUND_TYPE = Nearest
    SRC_ATTRS = elev_ca
    -> Tester
Tester
    BOOL_OP = OR
    COMPOSITE_TEST = 1
    TEST_CLAUSE = TEST @Value(elev_ca) >= 0
    TEST_MODE = TEST
    PASSED -> Junction
    FAILED -> AttributeCreator
AttributeCreator
    ATTR_TABLE = SET_TO elev_ca = 0
    -> Junction
Junction
    -> Tester_9
Tester_9
    BOOL_OP = OR
    COMPOSITE_TEST = 1
    TEST_CLAUSE = TEST wstar_id ATTRIBUTE_HAS_A_VALUE ""
    TEST_MODE = TEST
    PASSED -> well_s_pp (writer POSTGIS_2)
well_s_pp (writer POSTGIS_2)
    attributes: api varchar(8),BTree, surface_id int4, symnum int4, reliab varchar(2), long27 float8, lat27 float8, long83 float8, lat83 float8, wellid varchar(5), elev_ca int8, wstar_id varchar(14)
