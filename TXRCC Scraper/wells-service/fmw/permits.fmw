FME workspace permits.fmw

Parameters:
- DestDataset_POSTGIS_33 = pg.whitestar.com   # Connection

Writers:
- POSTGIS_1: POSTGIS to $(DestDataset_POSTGIS_33) in LL-27

Note: Node - srf_lng and lat are NAD27!
SQLCreator_3
    COORDSYS = LL27
    DATASET = pg.whitestar.com
    EXPOSED_ATTRIBUTE_LIST = api,elev_ca,lat83,long83,reliab,srf_lat,srf_lng,surface_id,symnum,wellid,wstar_id
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      api,
      elev_ca,
      lat27 as srf_lat,
      lat83,
      long27 as srf_lng,
      long83,
      reliab,
      surface_id,
      symnum,
      wellid,
      wstar_id,
      geom
      from well_s_pp
    RESULT -> FeatureJoiner_2 [LEFT]
SQLCreator_8
    DATASET = pg.whitestar.com
    EXPOSED_ATTRIBUTE_LIST = api,api10,apinum,bot_lat,bot_lng,bottom_id,lat83,long83,out_fips,radioactv,reliab,stcode,surface_id,symnum,well_num,wellid
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT:
      select distinct on (surface_id)
      api,
      api10,
      apinum,
      bottom_id,
      cwellnum as well_num,
      lat27 as bot_lat,
      lat83,
      long27 as bot_lng,
      long83,
      out_fips,
      radioact as radioactv,
      reliab,
      stcode,
      surface_id,
      symnum,
      wellid
      from well_b
    RESULT -> FeatureJoiner_2 [RIGHT]
FeatureJoiner_2
    ATTR_CONFLICT_RES = Use Left
    GEOMETRY_HANDLING = Use Left
    JOIN_KEYS = surface_id surface_id AUTO
    JOIN_MODE = Inner
    JOINED -> AttributeCreator_2
    UNJOINED_LEFT -> AttributeCreator_2
AttributeCreator_2
    ATTR_TABLE:
      SET_TO api_state = 42
      SET_TO state = TX
      SET_TO footage_1
      SET_TO footage_2
      SET_TO updt_date = @DateTimeNow()
      SET_TO data_src = TXRRC
    -> SubstringExtractor
Note: Extract API County Code
SubstringExtractor
    END = 2
    RESULT_ATTR = api_cnty
    SRC_STRING = @Value(api)
    START = 0
    -> AttributeTrimmer
AttributeTrimmer
    SRC_ATTRS = api_cnty
    TRIM_CHARS = 0
    TRIM_TO_NONE = Yes
    TRIM_TYPE = Left
    -> AttributeValueMapper_5
AttributeValueMapper_5
    DIRECTION = Forward (Source To Destination)
    LUT = 1,Anderson,101,Cottle,103,Crane,105,Crockett,107,Crosby,109,Culberson,11,Armstrong,111,Dallam,113,Dallas,115,Dawson,117,Deaf Smith,119,Delta,121,Denton,123,De Witt,125,Dickens,127,Dimmit,129,Donley,13,Atascosa,131,Duval,133,Eastland,135,Ector,137,Edwards,139,Ellis,141,El Paso,143,Erath,145,Falls,147,Fannin,149,Fayette,15,Austin,151,Fisher,153,Floyd,155,Foard,157,Fort Bend,159,Franklin,161,Freestone,163,Frio,165,Gaines,167,Galveston,169,Garza,17,Bailey,171,Gillespie,173,Glasscock,175,Goliad,177,Gonzales,179,Gray,181,Grayson,183,Gregg,185,Grimes,187,Guadalupe,189,Hale,19,Bandera,191,Hall,193,Hamilton,195,Hansford,197,Hardeman,199,Hardin,201,Harris,203,Harrison,205,Hartley,207,Haskell,209,Hays,21,Bastrop,211,Hemphill,213,Henderson,215,Hidalgo,217,Hill,219,Hockley,221,Hood,223,Hopkins,225,Houston,227,Howard,229,Hudspeth,23,Baylor,231,Hunt,233,Hutchinson,235,Irion,237,Jack,239,Jackson,241,Jasper,243,Jeff Davis,245,Jefferson,247,Jim Hogg,249,Jim Wells,25,Bee,251,Johnson,253,Jones,255,Karnes,257,Kaufman,259,Kendall,261,Kenedy,263,Kent,265,Kerr,267,Kimble,269,King,27,Bell,271,Kinney,273,Kleberg,275,Knox,277,Lamar,279,Lamb,281,Lampasas,283,La Salle,285,Lavaca,287,Lee,289,Leon,29,Bexar,291,Liberty,293,Limestone,295,Lipscomb,297,Live Oak,299,Llano,3,Andrews,301,Loving,303,Lubbock,305,Lynn,307,McCulloch,309,McLennan,31,Blanco,311,McMullen,313,Madison,315,Marion,317,Martin,319,Mason,321,Matagorda,323,Maverick,325,Medina,327,Menard,329,Midland,33,Borden,331,Milam,333,Mills,335,Mitchell,337,Montague,339,Montgomery,341,Moore,343,Morris,345,Motley,347,Nacogdoches,349,Navarro,35,Bosque,351,Newton,353,Nolan,355,Nueces,357,Ochiltree,359,Oldham,361,Orange,363,Palo Pinto,365,Panola,367,Parker,369,Parmer,37,Bowie,371,Pecos,373,Polk,375,Potter,377,Presidio,379,Rains,381,Randall,383,Reagan,385,Real,387,Red River,389,Reeves,39,Brazoria,391,Refugio,393,Roberts,395,Robertson,397,Rockwall,399,Runnels,401,Rusk,403,Sabine,405,San Augustine,407,San Jacinto,409,San Patricio,41,Brazos,411,San Saba,413,Schleicher,415,Scurry,417,Shackelford,419,Shelby,421,Sherman,423,Smith,425,Somervell,427,Starr,429,Stephens,43,Brewster,431,Sterling,433,Stonewall,435,Sutton,437,Swisher,439,Tarrant,441,Taylor,443,Terrell,445,Terry,447,Throckmorton,449,Titus,45,Briscoe,451,Tom Green,453,Travis,455,Trinity,457,Tyler,459,Upshur,461,Upton,463,Uvalde,465,Val Verde,467,Van Zandt,469,Victoria,47,Brooks,471,Walker,473,Waller,475,Ward,477,Washington,479,Webb,481,Wharton,483,Wheeler,485,Wichita,487,Wilbarger,489,Willacy,49,Brown,491,Williamson,493,Wilson,495,Winkler,497,Wise,499,Wood,5,Angelina,501,Yoakum,503,Young,505,Zapata,507,Zavala,51,Burleson,53,Burnet,55,Caldwell,57,Calhoun,59,Callahan,61,Cameron,63,Camp,65,Carson,67,Cass,69,Castro,7,Aransas,71,Chambers,73,Cherokee,75,Childress,77,Clay,79,Cochran,81,Coke,83,Coleman,85,Collin,87,Collingsworth,89,Colorado,9,Archer,91,Comal,93,Comanche,95,Concho,97,Cooke,99,Coryell,600,S PADRE ISLAND SMALL BLK,601,N PADRE ISLAND SMALL BLK,602,MUSTANG ISLAND SMALL BLK,603,MATAGORDA ISL SMALL BLK,604,BRAZOS SMALL BLOCK,605,GALVESTON SMALL BLOCK,606,HIGH ISLAND SMALL BLOCK,701,S PADRE ISLAND LARGE BLK,702,N PADRE ISLAND LARGE BLK,703,MUSTANG ISLAND LARGE BLK,704,MATAGORDA ISL LARGE BLK,705,BRAZOS LARGE BLOCK,706,GALVESTON LARGE BLOCK,707,GALVESTON SOUTH,708,HIGH  ISLAND LARGE BLOCK,709,HIGH ISLAND SOUTH,710,HIGH ISLAND EAST,711,HIGH ISLAND EAST & SOUTH,712,MUSTANG ISLAND EAST,713,N PADRE ISLAND EAST,714,S PADRE ISLAND EAST,715,SABINE PASS,805,TBD/UNKNOWN,999,TBD/UNKNOWN
    SRC = api_cnty
    VAL_ATTR = county
    -> Tester
Tester
    BOOL_OP = AND
    COMPOSITE_TEST = 1 AND 2
    TEST_CLAUSE:
      TEST @Value(api_cnty) > 507
      CASE_INSENSITIVE_TEST @Value(api_cnty) NOT_CONTAINS G
    TEST_MODE = TEST
    PASSED -> Junction_8
    FAILED -> PointOnAreaOverlayer [POINT]
SQLCreator_9
    DATASET = pg.whitestar.com
    EXPOSED_ATTRIBUTE_LIST = amoddate,county,cty_api,cty_census,datum,gmoddate,postal,rrdist,source,st_api,st_census,state,stcty_api,stcty_census
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT = select * from tx_county_district
    RESULT -> PointOnAreaOverlayer [AREA]
PointOnAreaOverlayer
    ATTR_ACCUM_MODE = Prefix Incoming
    DEAGGREGATE_INPUT = Yes
    INCOMING_PREFIX = xx_
    OV_ATTR = _overlaps
    POLYS_FIRST = NO
    POINT -> Tester_4
Junction_8
    -> AttributeValueMapper
Note: Post Code lookup table
AttributeValueMapper
    DEFAULT_VALUE = LOC
    DIRECTION = Forward (Source To Destination)
    LUT = 10,PB,103,STO,104,INJ,105,INJ,106,INJ,107,INJ,108,OB,109,OB,11,INJ,110,OB,111,OB,112,SRV,113,SRV,114,SRV,115,SRV,116,P&A,117,P&A,118,P&A,119,P&A,12,TEST,121,BW,122,BW,123,BW,124,INJ,125,INJ,126,INJ,127,INJ,128,OB,129,OB,13,DIRLOC,130,OB,131,OB,132,SRV,133,SRV,134,SRV,135,SRV,136,P&A,137,P&A,138,P&A,139,P&A,140,STO,141,STO,142,STO,143,STO,144,INJ,145,INJ,146,INJ,147,INJ,148,OB,149,OB,15,UNKN,150,OB,151,OB,152,P&A,153,P&A,154,P&A,155,P&A,16,TEST,17,OS,18,GS,19,SHUTIN-OIL,2,LOC,20,SHUTIN-GAS,21,INJ,22,INJ,23,INJ,24,DERRICK,3,DRY,36,GEO,4,OIL,5,GAS,6,O&G,7,PO,73,BW,74,H2O,75,WSO,76,WSG,77,WSB,78,OB,79,OB,8,PG,80,OB,81,OB,86,HORDH,87,STKWLOC,88,STO,89,SRV,9,ABDN,90,SRV,91,SRV,92,SRV
    SRC = symnum
    VAL_ATTR = post_code
    -> DuplicateFilter_7
DuplicateFilter_7
    INPUT_ORDERED_CHOICE = No
    KEYATTR = surface_id
    UNIQUE -> Tester_3
Tester_3
    BOOL_OP = COMPOSITE
    COMPOSITE_TEST = 1 AND 2
    TEST_CLAUSE:
      TEST @Value(symnum) >= 74
      TEST @Value(symnum) <= 77
    TEST_MODE = TEST
    PASSED -> AttributeCreator_5
    FAILED -> Junction_10
AttributeCreator_5
    ATTR_TABLE = SET_TO freshwater = Y
    -> Junction_10
Junction_10
    -> FeatureJoiner [LEFT]
Junction_9
    -> PointOnAreaOverlayer_2 [POINT]
EsriReprojector_3
    DEST = ESRIWKT|GCS_North_American_1927|GEOGCS["GCS_North_American_1927",DATUM["D_North_American_1927",SPHEROID["Clarke_1866",6378206.4,294.9786982]],PRIMEM["Greenwich",0.0],UNIT["Degree",0.0174532925199433]]
    GEOTRANSFORMATION_DIRECTION = Forward
    INTERPOLATION_TYPE_NAME = Nearest Neighbor
    RASTER_CELL_SIZE = Preserve Cells
    RASTER_TOLERANCE = 0.0
    SOURCE = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    REPROJECTED -> Date_Range_Checks [Tester_10_Input]
tx_header_pre_cum (writer POSTGIS_1)
    attributes: wstar_id varchar(14),BTREE, api varchar(8),BTREE, api_state int2,BTREE, api_cnty int2,BTREE, state varchar(2),BTREE, county varchar(25),BTREE, srf_lat float8, srf_lng float8, bot_lat float8, bot_lng float8, rrdist varchar(3), post_code varchar(10), oil_lease varchar(12), gas_lease varchar(8), elev_gl int2, elev_kb int2, elev_df int2, elev_ca int2, well_name varchar(50), well_num varchar(6), operator varchar(50), field_nam varchar(50), well_type varchar(12), abs_num varchar(12), block_nam varchar(50), survey_num varchar(8), survey_nam text, srv_nam2 text, scr_fileno varchar(10), loc_desc text,
      miles_town float8, dir_town varchar(6), near_town varchar(14), dis_srvln varchar(50), dis_nwell varchar(50), wellb_abs varchar(6), wellb_srv text, wellb_blk varchar(10), wellb_sec varchar(8), wb_altsec varchar(6), wb_altabs varchar(6), ftg_src varchar(5), footage_1 int4, ftg1_dir varchar(14), footage_2 int4, ftg2_dir varchar(14), quad_name varchar(50), quad_code varchar(10), freshwater varchar(1), radioactv varchar(1), permit_num int4, prmt_date date, spud_date date, comp_date date, plug_date date, tot_depth int4, acres int4, bhdata1 varchar(6), oglease varchar(12), cum_oil float8,
      cum_gas float8, cum_cond int4, cum_csgd float8, nwells int4, nmon_oil int2, nmon_gas int2, nmon_cond int2, nmon_csgd int2, tpms_id int4, sys_nm varchar(50), systype varchar(1), diameter float4, commodity1 varchar(3), interstate varchar(1), status_cd varchar(1), dist_pipe int2, data_src varchar(5), surface_id int4,BTREE, updt_date date,BTREE

Bookmark: County code in API Number not match that in calculated point in polygon operation
Tester_4
    BOOL_OP = OR
    COMPOSITE_TEST = 1
    TEST_CLAUSE = TEST @Value(api_cnty) = @Value(xx_cty_api)
    TEST_MODE = TEST
    PASSED -> AttributeCopier_2
    FAILED -> AttributeCreator
Note: cty code mismatch
AttributeCreator
    ATTR_TABLE = SET_TO api_cty_mismatch_flag = T
    -> AttributeCopier_2
AttributeCopier_2
    ATTR_TABLE:
      COPY xx_cty_api > api_cnty
      COPY xx_county > county
      COPY xx_rrdist > rrdist
    -> BulkAttributeRemover
BulkAttributeRemover
    ATTR_EXP = xx_.*
    -> AttributeRemover
AttributeRemover
    REMOVE_ATTRS = _overlaps
    -> Junction_8

Bookmark: Merge WB01
SQLCreator_2
    DATASET = pg.whitestar.com
    EXPOSED_ATTRIBUTE_LIST = api,comp_date,shut_in_date,tot_depth
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select wb_api as api,
      wb_shut_in_date as shut_in_date,
      wb_total_depth as tot_depth,
      wb_orig_compl_date as comp_date
      from wb01
    RESULT -> FeatureJoiner [RIGHT]
Note: WB01 Merge
FeatureJoiner
    ATTR_CONFLICT_RES = Use Left
    GEOMETRY_HANDLING = Use Left
    JOIN_KEYS = api api AUTO
    JOIN_MODE = Inner
    JOINED -> Junction_3
    UNJOINED_LEFT -> Junction_3
Junction_3
    -> FeatureJoiner_3 [LEFT]

Bookmark: Merge WB02
SQLCreator_4
    DATASET = pg.whitestar.com
    EXPOSED_ATTRIBUTE_LIST = api,oil_lease,plug_date
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select
      wb_api as api,
      wb_oil_lse_nbr as oil_lease,
      wb_plug_date_ptr as plug_date
      from wb02
      where length(wb_oil_lse_nbr) > 0
    RESULT -> FeatureJoiner_3 [RIGHT]
Note: wb02 Merge
FeatureJoiner_3
    ATTR_CONFLICT_RES = Use Left
    GEOMETRY_HANDLING = Use Left
    JOIN_KEYS = api api AUTO
    JOIN_MODE = Inner
    JOINED -> DuplicateFilter
    UNJOINED_LEFT -> Junction
DuplicateFilter
    INPUT_ORDERED_CHOICE = No
    KEYATTR = surface_id
    UNIQUE -> Junction
Junction
    -> Tester_2

Bookmark: Format oglease, for example O-12345-13
Tester_2
    BOOL_OP = OR
    COMPOSITE_TEST = 1
    TEST_CLAUSE = TEST @Value(oil_lease) != ""
    TEST_MODE = TEST
    PASSED -> AttributeValueMapper_2
    FAILED -> Junction_9
AttributeValueMapper_2
    DIRECTION = Forward (Source To Destination)
    LUT = 1,01,2,02,3,03,4,04,5,05,6,06,6E,07,7B,08,7C,09,8,10,8A,11,9,13,10,14
    SRC = rrdist
    VAL_ATTR = rrdist_rrc
    -> StringFormatter_3
StringFormatter_3
    FORMAT = 05d
    SRC_ATTRS = oil_lease
    -> StringConcatenator_4
StringConcatenator_4
    ACTION = Create New Attribute
    PARM_LINE = fme_basicstring:2%17%1%18:O-@Value(oil_lease)-@Value(rrdist_rrc)
    VAL_ATTR = oglease
    -> Junction_9

Bookmark: Calculate Block Survey Abstract
SQLCreator_10
    DATASET = pg.whitestar.com
    EXPOSED_ATTRIBUTE_LIST = ABSNA,ABSNO,ABSOVNA,ABSOVNO,BLOCKNA,BLOCKNO,BLOOVNA,BLOOVNO,COUNTY,CTY_API,DISTRICT,LOTNA,LOTNO,POSTAL,SOURCE,SUBDNA,SUBDNO,SUROVNA,SUROVNO,SURVNA,SURVNO,TRACTNA,TRACTNO
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT = select * from "TX_ABSTRACT"
    RESULT -> PointOnAreaOverlayer_2 [AREA]
    RESULT -> EsriReprojector
PointOnAreaOverlayer_2
    ATTR_ACCUM_MODE = Merge Incoming
    ATTR_CONFLICT_RES = Use Original
    DEAGGREGATE_INPUT = Yes
    OV_ATTR = _overlaps
    POLYS_FIRST = NO
    POINT -> AttributeRenamer
AttributeRenamer
    ATTR_TABLE:
      RENAME_SET_DEFAULT BLOCKNA > block_nam
      RENAME_SET_DEFAULT SURVNA > survey_nam
      RENAME_SET_DEFAULT SURVNO > survey_num
      RENAME_SET_DEFAULT BLOCKNO > loc_desc
      RENAME_SET_DEFAULT ABSNO > abs_num
    -> PointOnAreaOverlayer_3 [POINT]

Bookmark: Reverse Geocoder
EsriReprojector
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> NeighborPairFinder [CANDIDATE]
EsriReprojector_2
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> NeighborPairFinder [BASE]
NeighborPairFinder
    KEYATTR = ABSNO
    MAX = 25000
    MINANGLE = 70
    MODE = Bases and Candidates
    MATCHED -> TestFilter
    UNMATCHED_BASE -> Tester_5
TestFilter
    DEFAULT_VALUE = <UNFILTERED>
    TEST_LIST:
      "BOOL_OP,OR,COMPOSITE_TEST,""""""1 OR 2"""""",TEST_CLAUSE,TEST @Value(_heading1) > 337.5
      TEST @Value(_heading1) <= 22.5",FEL,"BOOL_OP,AND,COMPOSITE_TEST,""""""1 AND 2"""""",TEST_CLAUSE,TEST @Value(_heading1) > 22.5
      TEST @Value(_heading1) <= 67.5",FNEL,"BOOL_OP,AND,COMPOSITE_TEST,""""""1 AND 2"""""",TEST_CLAUSE,TEST @Value(_heading1) > 67.5
      TEST @Value(_heading1) <= 112.5",FNL,"BOOL_OP,AND,COMPOSITE_TEST,""""""1 AND 2"""""",TEST_CLAUSE,TEST @Value(_heading1) > 112.5
      TEST @Value(_heading1) <= 157.5",FNWL,"BOOL_OP,AND,COMPOSITE_TEST,""""""1 AND 2"""""",TEST_CLAUSE,TEST @Value(_heading1) > 157.5
      TEST @Value(_heading1) <= 202.5",FWL,"BOOL_OP,AND,COMPOSITE_TEST,""""""1 AND 2"""""",TEST_CLAUSE,TEST @Value(_heading1) > 202.5
      TEST @Value(_heading1) <= 247.5",FSWL,"BOOL_OP,AND,COMPOSITE_TEST,""""""1 AND 2"""""",TEST_CLAUSE,TEST @Value(_heading1) > 247.5
      TEST @Value(_heading1) <= 292.5",FSL,"BOOL_OP,AND,COMPOSITE_TEST,""""""1 AND 2"""""",TEST_CLAUSE,TEST @Value(_heading1) > 292.5
      TEST @Value(_heading1) <= 337.5",FSEL
    FEL -> AttributeCreator_22
    FNEL -> AttributeCreator_34
    FNL -> AttributeCreator_24
    FNWL -> AttributeCreator_33
    FWL -> AttributeCreator_25
    FSWL -> AttributeCreator_32
    FSL -> AttributeCreator_26
    FSEL -> AttributeCreator_31
    <UNFILTERED> -> AttributeCreator_23
AttributeCreator_22
    ATTR_TABLE = SET_TO footage_1_dir = FEL
    -> TestFilter_2
AttributeCreator_34
    ATTR_TABLE = SET_TO footage_1_dir = FNEL
    -> TestFilter_2
AttributeCreator_24
    ATTR_TABLE = SET_TO footage_1_dir = FNL
    -> TestFilter_2
AttributeCreator_33
    ATTR_TABLE = SET_TO footage_1_dir = FNWL
    -> TestFilter_2
AttributeCreator_25
    ATTR_TABLE = SET_TO footage_1 = FWL
    -> TestFilter_2
AttributeCreator_32
    ATTR_TABLE = SET_TO footage_1_dir = FSWL
    -> TestFilter_2
AttributeCreator_26
    ATTR_TABLE = SET_TO footage_1_dir = FSL
    -> TestFilter_2
AttributeCreator_31
    ATTR_TABLE = SET_TO footage_1_dir = FSEL
    -> TestFilter_2
TestFilter_2
    DEFAULT_VALUE = <UNFILTERED>
    TEST_LIST:
      "BOOL_OP,OR,COMPOSITE_TEST,""""""1 OR 2"""""",TEST_CLAUSE,TEST @Value(_heading2) > 337.5
      TEST @Value(_heading2) <= 22.5",FEL,"BOOL_OP,AND,COMPOSITE_TEST,""""""1 AND 2"""""",TEST_CLAUSE,TEST @Value(_heading2) > 22.5
      TEST @Value(_heading2) <= 67.5",FNEL,"BOOL_OP,AND,COMPOSITE_TEST,""""""1 AND 2"""""",TEST_CLAUSE,TEST @Value(_heading2) > 67.5
      TEST @Value(_heading2) <= 112.5",FNL,"BOOL_OP,AND,COMPOSITE_TEST,""""""1 AND 2"""""",TEST_CLAUSE,TEST @Value(_heading2) > 112.5
      TEST @Value(_heading2) <= 157.5",FNWL,"BOOL_OP,AND,COMPOSITE_TEST,""""""1 AND 2"""""",TEST_CLAUSE,TEST @Value(_heading2) > 157.5
      TEST @Value(_heading2) <= 202.5",FWL,"BOOL_OP,AND,COMPOSITE_TEST,""""""1 AND 2"""""",TEST_CLAUSE,TEST @Value(_heading2) > 202.5
      TEST @Value(_heading2) <= 247.5",FSWL,"BOOL_OP,AND,COMPOSITE_TEST,""""""1 AND 2"""""",TEST_CLAUSE,TEST @Value(_heading2) > 247.5
      TEST @Value(_heading2) <= 292.5",FSL,"BOOL_OP,AND,COMPOSITE_TEST,""""""1 AND 2"""""",TEST_CLAUSE,TEST @Value(_heading2) > 292.5
      TEST @Value(_heading2) <= 337.5",FSEL
    FEL -> AttributeCreator_38
    FNEL -> AttributeCreator_37
    FNL -> AttributeCreator_36
    FNWL -> AttributeCreator_35
    FWL -> AttributeCreator_30
    FSWL -> AttributeCreator_29
    FSL -> AttributeCreator_28
    FSEL -> AttributeCreator_27
    <UNFILTERED> -> AttributeCreator_23
AttributeCreator_38
    ATTR_TABLE = SET_TO footage_2_dir = FEL
    -> AttributeCreator_23
AttributeCreator_37
    ATTR_TABLE = SET_TO footage_2_dir = FNEL
    -> AttributeCreator_23
AttributeCreator_36
    ATTR_TABLE = SET_TO footage_2_dir = FNL
    -> AttributeCreator_23
AttributeCreator_35
    ATTR_TABLE = SET_TO footage_2_dir = FNWL
    -> AttributeCreator_23
AttributeCreator_30
    ATTR_TABLE = SET_TO footage_2_dir = FWL
    -> AttributeCreator_23
AttributeCreator_29
    ATTR_TABLE = SET_TO footage_2_dir = FSWL
    -> AttributeCreator_23
AttributeCreator_28
    ATTR_TABLE = SET_TO footage_2_dir = FSL
    -> AttributeCreator_23
AttributeCreator_27
    ATTR_TABLE = SET_TO footage_2_dir = FSEL
    -> AttributeCreator_23
AttributeCreator_23
    ATTR_TABLE:
      SET_TO ftg_src = WS
      SET_TO footage_1 = @Value(_distance1)
      SET_TO footage_2 = @Value(_distance2)
    -> Tester_5
Tester_5
    BOOL_OP = OR
    COMPOSITE_TEST = 1
    TEST_CLAUSE = TEST footage_1 ATTRIBUTE_HAS_A_VALUE ""
    TEST_MODE = TEST
    PASSED -> AttributeRounder
    FAILED -> Tester_6
AttributeRounder
    PLACES = 0
    ROUND_TYPE = Nearest
    SRC_ATTRS = footage_1
    -> Tester_6
Tester_6
    BOOL_OP = OR
    COMPOSITE_TEST = 1
    TEST_CLAUSE = TEST footage_2 ATTRIBUTE_HAS_A_VALUE ""
    TEST_MODE = TEST
    PASSED -> AttributeRounder_3
    FAILED -> Tester_7
AttributeRounder_3
    PLACES = 0
    ROUND_TYPE = Nearest
    SRC_ATTRS = footage_2
    -> Tester_7
Tester_7
    BOOL_OP = OR
    COMPOSITE_TEST = 1
    TEST_CLAUSE = TEST _distance1 ATTRIBUTE_HAS_A_VALUE ""
    TEST_MODE = TEST
    PASSED -> AttributeRounder_4
    FAILED -> Tester_8
AttributeRounder_4
    PLACES = 0
    ROUND_TYPE = Nearest
    SRC_ATTRS = _distance1
    -> Tester_8
Tester_8
    BOOL_OP = OR
    COMPOSITE_TEST = 1
    TEST_CLAUSE = TEST _distance2 ATTRIBUTE_HAS_A_VALUE ""
    TEST_MODE = TEST
    PASSED -> AttributeRounder_5
    FAILED -> Junction_7
AttributeRounder_5
    PLACES = 0
    ROUND_TYPE = Nearest
    SRC_ATTRS = _distance2
    -> Junction_7
Junction_7
    -> AttributeRenamer_5

Bookmark: Calculate Topo Map Names
SQLCreator_11
    DATASET = pg.whitestar.com
    EXPOSED_ATTRIBUTE_LIST = LAT,LONG,QUAD,SCALE,STATE,USGS
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select * from "MRG_TOPO"
      where "STATE" like '%TX%'
    RESULT -> PointOnAreaOverlayer_3 [AREA]
PointOnAreaOverlayer_3
    ATTR_ACCUM_MODE = Prefix Incoming
    DEAGGREGATE_INPUT = Yes
    INCOMING_PREFIX = topo_
    OV_ATTR = _overlaps
    POLYS_FIRST = NO
    POINT -> AttributeRenamer_9
AttributeRenamer_9
    ATTR_TABLE:
      RENAME_SET_DEFAULT topo_QUAD > quad_name
      RENAME_SET_DEFAULT topo_USGS > quad_code
    -> EsriReprojector_2

Bookmark: Merge WB13 - New Location Data. (Very few records reference the old)
AttributeRenamer_5
    ATTR_TABLE:
      RENAME_SET_DEFAULT footage_1_dir > ftg1_dir
      RENAME_SET_DEFAULT footage_2_dir > ftg2_dir
      RENAME_SET_DEFAULT ABSNO > abs_num
    -> FeatureJoiner_4 [LEFT]
SQLCreator_5
    DATASET = pg.whitestar.com
    EXPOSED_ATTRIBUTE_LIST = api,footage_1,footage_2,ftg1_dir,ftg2_dir,wb_altabs,wb_altsec,wb_blk,wellb_abs,wellb_sec,wellb_srv
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select wb_api as api,
      wb_abstract as wellb_abs,
      wb_survey as wellb_srv,
      wb_section as wellb_sec,
      wb_alt_abstract as wb_altabs,
      wb_alt_section as wb_altsec,
      wb_block_number as wb_blk,
      wb_feet_from_sur_sect_1 as footage_1,
      wb_feet_from_sur_sect_2 as footage_2,
      wb_direc_from_ur_ect_1 as ftg1_dir,
      wb_direc_from_sur_sect_2 as ftg2_dir
      from wb13
      where wb_feet_from_sur_sect_1 > 0 and wb_feet_from_sur_sect_2 > 0;
    RESULT -> FeatureJoiner_4 [RIGHT]
Note: wb13 Merge
FeatureJoiner_4
    ATTR_CONFLICT_RES = Use Left
    GEOMETRY_HANDLING = Use Left
    JOIN_KEYS = api api AUTO
    JOIN_MODE = Inner
    JOINED -> AttributeCreator_4
    UNJOINED_LEFT -> Junction_2
AttributeCreator_4
    ATTR_TABLE = SET_TO ftg_src = TXRRC
    -> Junction_2
Junction_2
    -> AttributeRemover_2
AttributeRemover_2
    REMOVE_ATTRS = _candidate_angle1,_candidate_angle2,_candidate_label_angle1,_candidate_label_angle2,_closest_base_x1,_closest_base_x2,_closest_base_y1,_closest_base_y2,_closest_candidate_x1,_closest_candidate_x2,_closest_candidate_y1,_closest_candidate_y2,_distance1,_distance2,_heading1,_heading2,_key1,_key2,_length,_overlaps
    -> FeatureJoiner_5 [LEFT]

Bookmark: Merge API File
SQLCreator_6
    DATASET = pg.whitestar.com
    EXPOSED_ATTRIBUTE_LIST = abstract,api,apinum,block,completion_date,field_nam,field_name,gas_lease,gas_rrcid,lease_name,oil_gas_co,on_off_sch,operator,permit_num,plug_date,quadnum,refer_to_a,section,survey,tot_depth,total_dept,well_name,wellid
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select apinum as api,
      field_name as field_nam,
      lease_name as well_name,
      gas_rrcid as gas_lease,
      total_dept as tot_depth,
      *
      from txapi
      order by total_dept, gas_rrcid desc;
    RESULT -> FeatureJoiner_5 [RIGHT]
Note: tx_api Merge
FeatureJoiner_5
    ATTR_CONFLICT_RES = Use Left
    GEOMETRY_HANDLING = Use Left
    JOIN_KEYS = api api AUTO
    JOIN_MODE = Inner
    JOINED -> DuplicateFilter_2
    UNJOINED_LEFT -> Junction_4
DuplicateFilter_2
    INPUT_ORDERED_CHOICE = No
    KEYATTR = surface_id
    UNIQUE -> StringFormatter_2
StringFormatter_2
    FORMAT = 06d
    SRC_ATTRS = gas_lease
    -> Junction_4
Junction_4
    -> FeatureJoiner_6 [LEFT]

Bookmark: Break out elevations by GL, KB and DF. Note that DF and RT are put together as are GL and GR Wellbore codes
SQLCreator_7
    DATASET = pg.whitestar.com
    EXPOSED_ATTRIBUTE_LIST = api,wb_elevation,wb_elevation_code
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select distinct
      wb_api as api,
      wb_elevation_code,
      wb_elevation
      from wb03
      where wb_elevation != '0'
      order by wb_elevation desc
    RESULT -> FeatureJoiner_6 [RIGHT]
Note: wb03 merge
FeatureJoiner_6
    ATTR_CONFLICT_RES = Use Left
    GEOMETRY_HANDLING = Use Left
    JOIN_KEYS = api api AUTO
    JOIN_MODE = Inner
    JOINED -> DuplicateFilter_5
    UNJOINED_LEFT -> Junction_5
DuplicateFilter_5
    INPUT_ORDERED_CHOICE = No
    KEYATTR = surface_id
    UNIQUE -> TestFilter_3
TestFilter_3
    DEFAULT_VALUE = <UNFILTERED>
    TEST_LIST:
      "BOOL_OP,OR,COMPOSITE_TEST,""""""1 OR 2"""""",TEST_CLAUSE,TEST @Value(wb_elevation_code) = DF
      TEST @Value(wb_elevation_code) = RT",DF,"BOOL_OP,COMPOSITE,COMPOSITE_TEST,""""""1 OR 2"""""",TEST_CLAUSE,TEST @Value(wb_elevation_code) = GL
      TEST @Value(wb_elevation_code) = GR",GL,"BOOL_OP,OR,COMPOSITE_TEST,""""""1"""""",TEST_CLAUSE,TEST @Value(wb_elevation_code) = KB",KB,"BOOL_OP,AND,COMPOSITE_TEST,""""""1"""""",TEST_CLAUSE,TEST @Value(wb_elevation) > 0",No Etype
    DF -> AttributeCreator_6
    GL -> AttributeCreator_7
    KB -> AttributeCreator_8
    No Etype -> AttributeCreator_7
    <UNFILTERED> -> Junction_5
AttributeCreator_6
    ATTR_TABLE = SET_TO elev_df = @Value(wb_elevation)
    -> Junction_5
AttributeCreator_8
    ATTR_TABLE = SET_TO elev_kb = @Value(wb_elevation)
    -> Junction_5
AttributeCreator_7
    ATTR_TABLE = SET_TO elev_gl = @Value(wb_elevation)
    -> Junction_5
Junction_5
    -> FeatureJoiner_7 [LEFT]

Bookmark: Permits - Merge in Data from Earliest recorded Permit - da_permit_sequence_number = '99'
SQLCreator
    DATASET = pg.whitestar.com
    EXPOSED_ATTRIBUTE_LIST = acres,api,dir_town,dis_nwell,dis_srvln,miles_town,near_town,prmt_date,spud_date,well_type
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    POSTGRES_SCHEMAS_FOR_TABLE_LISTING = public
    SQL_STATEMENT:
      select distinct on (api_number)
      api_number as api,
      da_permit_issued_date as prmt_date,
      da_permit_spud_date as spud_date,
      da_surface_miles_from_city as miles_town,
      da_surface_nearest_city as near_town,
      da_surface_direction_from_city as dir_town,
      da_old_survey_distance as dis_srvln,
      da_nearest_well as dis_nwell,
      da_surface_acres as acres,
      da_well_status as well_type
      from perm02 where da_permit_sequence_number = '99'
    RESULT -> FeatureJoiner_7 [RIGHT]
Note: permit2 Merge
FeatureJoiner_7
    ATTR_CONFLICT_RES = Use Left
    GEOMETRY_HANDLING = Use Left
    JOIN_KEYS = api api AUTO
    JOIN_MODE = Inner
    JOINED -> Junction_6
    UNJOINED_LEFT -> Junction_6
Junction_6
    -> EsriReprojector_3

Bookmark: Final Clean / Checks
Date_Range_Checks: Date Range Checks
    ABSNA = @Value(ABSNA)
    ABSOVNA = @Value(ABSOVNA)
    ABSOVNO = @Value(ABSOVNO)
    ABSTRACT = @Value(abstract)
    ABS_NUM = @Value(abs_num)
    ACRES = @Value(acres)
    API = @Value(api)
    API10 = @Value(api10)
    APINUM = @Value(apinum)
    API_CNTY = @Value(api_cnty)
    API_CTY_MISMATCH_FLAG = @Value(api_cty_mismatch_flag)
    API_STATE = @Value(api_state)
    BLOCK = @Value(block)
    BLOCK_NAM = @Value(block_nam)
    BLOOVNA = @Value(BLOOVNA)
    BLOOVNO = @Value(BLOOVNO)
    BOTTOM_ID = @Value(bottom_id)
    BOT_LAT = @Value(bot_lat)
    BOT_LNG = @Value(bot_lng)
    COMPLETION_DATE = @Value(completion_date)
    COMP_DATE = @Value(comp_date)
    COUNTY = @Value(county)
    COUNTY_2 = @Value(COUNTY)
    CTY_API = @Value(CTY_API)
    DATA_SRC = @Value(data_src)
    DIR_TOWN = @Value(dir_town)
    DISTRICT = @Value(DISTRICT)
    DIS_NWELL = @Value(dis_nwell)
    DIS_SRVLN = @Value(dis_srvln)
    ELEV_CA = @Value(elev_ca)
    ELEV_DF = @Value(elev_df)
    ELEV_GL = @Value(elev_gl)
    ELEV_KB = @Value(elev_kb)
    FIELD_NAM = @Value(field_nam)
    FIELD_NAME = @Value(field_name)
    FOOTAGE_1 = @Value(footage_1)
    FOOTAGE_2 = @Value(footage_2)
    FRESHWATER = @Value(freshwater)
    FTG1_DIR = @Value(ftg1_dir)
    FTG2_DIR = @Value(ftg2_dir)
    FTG_SRC = @Value(ftg_src)
    GAS_LEASE = @Value(gas_lease)
    GAS_RRCID = @Value(gas_rrcid)
    LAT83 = @Value(lat83)
    LEASE_NAME = @Value(lease_name)
    LOC_DESC = @Value(loc_desc)
    LONG83 = @Value(long83)
    LOTNA = @Value(LOTNA)
    LOTNO = @Value(LOTNO)
    MILES_TOWN = @Value(miles_town)
    NEAR_TOWN = @Value(near_town)
    OGLEASE = @Value(oglease)
    OIL_GAS_CO = @Value(oil_gas_co)
    OIL_LEASE = @Value(oil_lease)
    ON_OFF_SCH = @Value(on_off_sch)
    OPERATOR = @Value(operator)
    OUT_FIPS = @Value(out_fips)
    PERMIT_NUM = @Value(permit_num)
    PLUG_DATE = @Value(plug_date)
    POSTAL = @Value(POSTAL)
    POST_CODE = @Value(post_code)
    PRMT_DATE = @Value(prmt_date)
    QUADNUM = @Value(quadnum)
    QUAD_CODE = @Value(quad_code)
    QUAD_NAME = @Value(quad_name)
    RADIOACTV = @Value(radioactv)
    REFER_TO_A = @Value(refer_to_a)
    RELIAB = @Value(reliab)
    RRDIST = @Value(rrdist)
    RRDIST_RRC = @Value(rrdist_rrc)
    SECTION = @Value(section)
    SHUT_IN_DATE = @Value(shut_in_date)
    SOURCE = @Value(SOURCE)
    SPUD_DATE = @Value(spud_date)
    SRF_LAT = @Value(srf_lat)
    SRF_LNG = @Value(srf_lng)
    STATE = @Value(state)
    STCODE = @Value(stcode)
    SUBDNA = @Value(SUBDNA)
    SUBDNO = @Value(SUBDNO)
    SURFACE_ID = @Value(surface_id)
    SUROVNA = @Value(SUROVNA)
    SUROVNO = @Value(SUROVNO)
    SURVEY = @Value(survey)
    SURVEY_NAM = @Value(survey_nam)
    SURVEY_NUM = @Value(survey_num)
    SYMNUM = @Value(symnum)
    TOPO_LAT = @Value(topo_LAT)
    TOPO_LONG = @Value(topo_LONG)
    TOPO_SCALE = @Value(topo_SCALE)
    TOPO_STATE = @Value(topo_STATE)
    TOTAL_DEPT = @Value(total_dept)
    TOT_DEPTH = @Value(tot_depth)
    TRACTNA = @Value(TRACTNA)
    TRACTNO = @Value(TRACTNO)
    UPDT_DATE = @Value(updt_date)
    WB_ALTABS = @Value(wb_altabs)
    WB_ALTSEC = @Value(wb_altsec)
    WB_BLK = @Value(wb_blk)
    WB_ELEVATION = @Value(wb_elevation)
    WB_ELEVATION_CODE = @Value(wb_elevation_code)
    WELLB_ABS = @Value(wellb_abs)
    WELLB_SEC = @Value(wellb_sec)
    WELLB_SRV = @Value(wellb_srv)
    WELLID = @Value(wellid)
    WELL_NAME = @Value(well_name)
    WELL_NUM = @Value(well_num)
    WELL_TYPE = @Value(well_type)
    WSTAR_ID = @Value(wstar_id)
    Tester_15_Passed -> StringCaseChanger
    AttributeCreator_12_Output -> StringCaseChanger
StringCaseChanger
    ATTRCHOICE = All Attributes
    CHANGE_TYPE = UPPERCASE
    -> StringPadder_11
StringPadder_11
    BLANK_ATTRIBUTE = Yes
    PADCHAR = 0
    SIDE = Right
    SRC_ATTRS = wstar_id
    WIDTH = 14
    -> Sorter
Sorter
    SORT_PARM = api_cnty NUMERIC ASCENDING
    SORTED -> tx_header_pre_cum (writer POSTGIS_1)

FME custom transformer Date Range Checks

Parameters:
- SPUD_DATE = @Value(spud_date)   # Spud Date
- PLUG_DATE = @Value(plug_date)   # Plug Date
- PRMT_DATE = @Value(prmt_date)   # Prmt Date
- COMP_DATE = @Value(comp_date)   # Comp Date
- ABS_NUM = @Value(abs_num)   # Abs Num
- ABSNA = @Value(ABSNA)
- ABSOVNA = @Value(ABSOVNA)
- ABSOVNO = @Value(ABSOVNO)
- ABSTRACT = @Value(abstract)   # abstract
- ACRES = @Value(acres)   # acres
- API = @Value(api)   # api
- API_CNTY = @Value(api_cnty)   # Api Cnty
- API_CTY_MISMATCH_FLAG = @Value(api_cty_mismatch_flag)   # Api Cty Mismatch Flag
- API_STATE = @Value(api_state)   # Api State
- API10 = @Value(api10)   # api10
- APINUM = @Value(apinum)   # apinum
- BLOCK = @Value(block)   # block
- BLOCK_NAM = @Value(block_nam)   # Block Nam
- BLOOVNA = @Value(BLOOVNA)
- BLOOVNO = @Value(BLOOVNO)
- BOT_LAT = @Value(bot_lat)   # Bot Lat
- BOT_LNG = @Value(bot_lng)   # Bot Lng
- BOTTOM_ID = @Value(bottom_id)   # Bottom Id
- COMPLETION_DATE = @Value(completion_date)   # Completion Date
- COUNTY = @Value(county)   # county
- COUNTY_2 = @Value(COUNTY)   # COUNTY
- CTY_API = @Value(CTY_API)   # Cty Api
- DATA_SRC = @Value(data_src)   # Data Src
- DIR_TOWN = @Value(dir_town)   # Dir Town
- DIS_NWELL = @Value(dis_nwell)   # Dis Nwell
- DIS_SRVLN = @Value(dis_srvln)   # Dis Srvln
- DISTRICT = @Value(DISTRICT)
- ELEV_CA = @Value(elev_ca)   # Elev Ca
- ELEV_DF = @Value(elev_df)   # Elev Df
- ELEV_GL = @Value(elev_gl)   # Elev Gl
- ELEV_KB = @Value(elev_kb)   # Elev Kb
- FIELD_NAM = @Value(field_nam)   # Field Nam
- FIELD_NAME = @Value(field_name)   # Field Name
- FOOTAGE_1 = @Value(footage_1)   # Footage 1
- FOOTAGE_2 = @Value(footage_2)   # Footage 2
- FRESHWATER = @Value(freshwater)   # freshwater
- FTG_SRC = @Value(ftg_src)   # Ftg Src
- FTG1_DIR = @Value(ftg1_dir)   # Ftg1 Dir
- FTG2_DIR = @Value(ftg2_dir)   # Ftg2 Dir
- GAS_LEASE = @Value(gas_lease)   # Gas Lease
- GAS_RRCID = @Value(gas_rrcid)   # Gas Rrcid
- LAT83 = @Value(lat83)   # lat83
- LEASE_NAME = @Value(lease_name)   # Lease Name
- LOC_DESC = @Value(loc_desc)   # Loc Desc
- LONG83 = @Value(long83)   # long83
- LOTNA = @Value(LOTNA)
- LOTNO = @Value(LOTNO)
- MILES_TOWN = @Value(miles_town)   # Miles Town
- NEAR_TOWN = @Value(near_town)   # Near Town
- OGLEASE = @Value(oglease)   # oglease
- OIL_GAS_CO = @Value(oil_gas_co)   # Oil Gas Co
- OIL_LEASE = @Value(oil_lease)   # Oil Lease
- ON_OFF_SCH = @Value(on_off_sch)   # On Off Sch
- OPERATOR = @Value(operator)   # operator
- OUT_FIPS = @Value(out_fips)   # Out Fips
- PERMIT_NUM = @Value(permit_num)   # Permit Num
- POST_CODE = @Value(post_code)   # Post Code
- POSTAL = @Value(POSTAL)
- QUAD_CODE = @Value(quad_code)   # Quad Code
- QUAD_NAME = @Value(quad_name)   # Quad Name
- QUADNUM = @Value(quadnum)   # quadnum
- RADIOACTV = @Value(radioactv)   # radioactv
- REFER_TO_A = @Value(refer_to_a)   # Refer To A
- RELIAB = @Value(reliab)   # reliab
- RRDIST = @Value(rrdist)   # rrdist
- RRDIST_RRC = @Value(rrdist_rrc)   # Rrdist Rrc
- SECTION = @Value(section)   # section
- SHUT_IN_DATE = @Value(shut_in_date)   # Shut In Date
- SOURCE = @Value(SOURCE)
- SRF_LAT = @Value(srf_lat)   # Srf Lat
- SRF_LNG = @Value(srf_lng)   # Srf Lng
- STATE = @Value(state)   # state
- STCODE = @Value(stcode)   # stcode
- SUBDNA = @Value(SUBDNA)
- SUBDNO = @Value(SUBDNO)
- SURFACE_ID = @Value(surface_id)   # Surface Id
- SUROVNA = @Value(SUROVNA)
- SUROVNO = @Value(SUROVNO)
- SURVEY = @Value(survey)   # survey
- SURVEY_NAM = @Value(survey_nam)   # Survey Nam
- SURVEY_NUM = @Value(survey_num)   # Survey Num
- SYMNUM = @Value(symnum)   # symnum
- TOPO_LAT = @Value(topo_LAT)   # Topo Lat
- TOPO_LONG = @Value(topo_LONG)   # Topo Long
- TOPO_SCALE = @Value(topo_SCALE)   # Topo Scale
- TOPO_STATE = @Value(topo_STATE)   # Topo State
- TOT_DEPTH = @Value(tot_depth)   # Tot Depth
- TOTAL_DEPT = @Value(total_dept)   # Total Dept
- TRACTNA = @Value(TRACTNA)
- TRACTNO = @Value(TRACTNO)
- UPDT_DATE = @Value(updt_date)   # Updt Date
- WB_ALTABS = @Value(wb_altabs)   # Wb Altabs
- WB_ALTSEC = @Value(wb_altsec)   # Wb Altsec
- WB_BLK = @Value(wb_blk)   # Wb Blk
- WB_ELEVATION = @Value(wb_elevation)   # Wb Elevation
- WB_ELEVATION_CODE = @Value(wb_elevation_code)   # Wb Elevation Code
- WELL_NAME = @Value(well_name)   # Well Name
- WELL_NUM = @Value(well_num)   # Well Num
- WELL_TYPE = @Value(well_type)   # Well Type
- WELLB_ABS = @Value(wellb_abs)   # Wellb Abs
- WELLB_SEC = @Value(wellb_sec)   # Wellb Sec
- WELLB_SRV = @Value(wellb_srv)   # Wellb Srv
- WELLID = @Value(wellid)   # wellid
- WSTAR_ID = @Value(wstar_id)   # Wstar Id

Tester_10_Input (input)
    -> Tester_10
Tester_10
    BOOL_OP = OR
    COMPOSITE_TEST = 1
    TEST_CLAUSE = TEST prmt_date ATTRIBUTE_HAS_A_VALUE ""
    TEST_MODE = TEST
    PASSED -> Tester_9
    FAILED -> AttributeCreator_9
Tester_9
    BOOL_OP = OR
    COMPOSITE_TEST = 1
    TEST_CLAUSE = NUM_TEST @Value(prmt_date) RANGE [18000101,20200630]
    TEST_MODE = NUM_TEST
    PASSED -> Tester_12
    FAILED -> AttributeCreator_9
AttributeCreator_9
    ATTR_TABLE = SET_TO prmt_date = FME_NULL_VALUE
    -> Tester_12
Tester_12
    BOOL_OP = OR
    COMPOSITE_TEST = 1
    TEST_CLAUSE = TEST spud_date ATTRIBUTE_HAS_A_VALUE ""
    TEST_MODE = TEST
    PASSED -> Tester_11
    FAILED -> AttributeCreator_10
Tester_11
    BOOL_OP = OR
    COMPOSITE_TEST = 1
    TEST_CLAUSE = NUM_TEST @Value(spud_date) RANGE [18000101,20200630]
    TEST_MODE = NUM_TEST
    PASSED -> Tester_14
    FAILED -> AttributeCreator_10
AttributeCreator_10
    ATTR_TABLE = SET_TO spud_date = FME_NULL_VALUE
    -> Tester_14
Tester_14
    BOOL_OP = OR
    COMPOSITE_TEST = 1
    TEST_CLAUSE = TEST comp_date ATTRIBUTE_HAS_A_VALUE ""
    TEST_MODE = TEST
    PASSED -> Tester_13
    FAILED -> AttributeCreator_11
Tester_13
    BOOL_OP = OR
    COMPOSITE_TEST = 1
    TEST_CLAUSE = NUM_TEST @Value(comp_date) RANGE [18000101,20200630]
    TEST_MODE = NUM_TEST
    PASSED -> Tester_16
    FAILED -> AttributeCreator_11
AttributeCreator_11
    ATTR_TABLE = SET_TO comp_date = FME_NULL_VALUE
    -> Tester_16
Tester_16
    BOOL_OP = OR
    COMPOSITE_TEST = 1
    TEST_CLAUSE = TEST plug_date ATTRIBUTE_HAS_A_VALUE ""
    TEST_MODE = TEST
    PASSED -> Tester_15
    FAILED -> AttributeCreator_12
Tester_15
    BOOL_OP = OR
    COMPOSITE_TEST = 1
    TEST_CLAUSE = NUM_TEST @Value(plug_date) RANGE [18000101,20200630]
    TEST_MODE = NUM_TEST
    PASSED -> Tester_15_Passed (output)
    FAILED -> AttributeCreator_12
Tester_15_Passed (output)
AttributeCreator_12
    ATTR_TABLE = SET_TO plug_date = FME_NULL_VALUE
    -> AttributeCreator_12_Output (output)
AttributeCreator_12_Output (output)
