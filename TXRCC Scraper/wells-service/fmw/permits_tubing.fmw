FME workspace permits_tubing.fmw

Parameters:
- DestDataset_POSTGIS = pg.whitestar.com   # Connection

Writers:
- POSTGIS_1: POSTGIS to $(DestDataset_POSTGIS)

SQLCreator_4
    COORDSYS = LL27
    DATASET = pg.whitestar.com
    EXPOSED_ATTRIBUTE_LIST = api,api_cnty,api_state,county,state,wstar_id
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select *
      from tx_header_pre_cum
      where length(api) = 8
    RESULT -> FeatureJoiner [LEFT]
SQLCreator_2
    DATASET = pg.whitestar.com
    EXPOSED_ATTRIBUTE_LIST = api,depth_set,packer_set,seg_cntr,tubng_denm,tubng_inch,tubng_numr
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT:
      select distinct
      wb_api as api,
      wb_segment_counter as seg_cntr,
      wb_tubing_inches as tubng_inch,
      wb_tubing_numerator as tubng_numr,
      wb_tubing_denominator as tubng_denm,
      wb_depth_set as depth_set,
      wb_packer_set as packer_set
      from wb05
    RESULT -> FeatureJoiner [RIGHT]
FeatureJoiner
    ATTR_CONFLICT_RES = Use Left
    GEOMETRY_HANDLING = Use Left
    JOIN_KEYS = api api AUTO
    JOIN_MODE = Inner
    JOINED -> StringLengthCalculator_3
AttributeCreator_4
    ATTR_TABLE = SET_TO api = @Value(wstar_id)
    -> Sorter
Sorter
    SORT_PARM = api ALPHA ASCENDING tubng_numr NUMERIC ASCENDING
    SORTED -> tx_tubing_latest_build (writer POSTGIS_1)
tx_tubing_latest_build (writer POSTGIS_1)
    attributes: wstar_id varchar(14),BTree, api varchar(14),BTree, api_state int2, api_cnty int2,BTree, state char(2), county varchar(25),BTree, seg_cntr int2, tubng_inch int2, tubng_numr int2, tubng_denm int2, depth_set int2, packer_set int4

Bookmark: wstar_id Check/Correct
StringLengthCalculator_3
    LENGTH_ATTR = _length_wstar_id
    SRC_ATTR = wstar_id
    -> Tester_2
Tester_2
    BOOL_OP = OR
    COMPOSITE_TEST = 1
    TEST_CLAUSE = TEST @Value(_length_wstar_id) < 14
    TEST_MODE = TEST
    PASSED -> StringPadder_3
    FAILED -> AttributeCreator_4
StringPadder_3
    BLANK_ATTRIBUTE = Yes
    PADCHAR = 0
    SIDE = Right
    SRC_ATTRS = wstar_id
    WIDTH = 14
    <REJECTED> -> AttributeCreator_4
