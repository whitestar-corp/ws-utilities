FME workspace loadpipelines (backup).fmw

Parameters:
- DestDataset_POSTGIS = pg.whitestar.com   # Connection
- SourceDataset_SHAPEFILE_3 = D:\Users\rwhite\Documents\texas-wells\piplines\data\pipe*.shp   # Source Esri Shapefile(s)
- FEATURE_TYPES_2 =

Readers:
- SHAPEFILE_1: SHAPEFILE from $(SourceDataset_SHAPEFILE_3) in EPSG:4267

Writers:
- POSTGIS_2: POSTGIS to $(DestDataset_POSTGIS)

pipe001l (reader SHAPEFILE_1)
    attributes: TPMS_ID long, OPER_LINK long, OPS_ID long, P5_NUM char(6), OPER_NM char(40), SYS_NM char(40), SUBSYS_NM char(40), T4PERMIT char(5), DIAMETER float, COMMODITY1 char(3), COMMODITY2 char(3), COMMODITY3 char(3), CMDTY_DESC char(40), INTERSTATE char(1), STATUS_CD char(1), QUALITY_CD char(1), SYSTYPE char(1), COUNTY char(3), COM_CARRIE char(1), PLINE_ID char(20), SYS_ID char(6), NPMS_SYS_I long, ALBERS_MIL double, LENGTH double
    -> BulkAttributeRenamer
BulkAttributeRenamer
    ATTRCHOICE = All Attributes
    CASE_CHANGE_TYPE = lower
    MODE_CHOICE = RENAME
    PATTERN_ACTION_DISP = CASECHANGE
    -> tx_pipelines_for_wells (writer POSTGIS_2)
tx_pipelines_for_wells (writer POSTGIS_2)
    attributes: tpms_id int4, oper_link int4, ops_id int4, p5_num varchar(6), oper_nm varchar(40), sys_nm varchar(40), subsys_nm varchar(40), t4permit varchar(5), diameter float4, commodity1 varchar(3), commodity2 varchar(3), commodity3 varchar(3), cmdty_desc varchar(40), interstate varchar(1), status_cd varchar(1), quality_cd varchar(1), systype varchar(1), county varchar(3), com_carrie varchar(1), pline_id varchar(20), sys_id varchar(6), npms_sys_i int4, albers_mil float8, length float8
