FME workspace giswell2pg.fmw

Parameters:
- SourceDataset_SHAPEFILE_5 = D:\Users\rwhite\Documents\texas-wells\wells-service\data\wells\well*b.shp   # Source Esri Shapefile(s)
- FEATURE_TYPES_2 =
- SourceDataset_SHAPEFILE_4 = D:\Users\rwhite\Documents\texas-wells\wells-service\data\wells\well*l.shp   # Source Esri Shapefile(s)
- FEATURE_TYPES_3 =
- SourceDataset_SHAPEFILE = D:\Users\rwhite\Documents\texas-wells\wells-service\data\wells\well*s.shp   # Source Esri Shapefile(s)
- FEATURE_TYPES =
- DestDataset_POSTGIS = pg.whitestar.com   # Connection
- DestDataset_POSTGIS_5 = pg.whitestar.com   # Connection
- DestDataset_POSTGIS_4 = pg.whitestar.com   # Connection

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_4)

Writers:
- POSTGIS_1: POSTGIS to $(DestDataset_POSTGIS)
- POSTGIS_2: POSTGIS to $(DestDataset_POSTGIS_5)
- POSTGIS_3: POSTGIS to $(DestDataset_POSTGIS_4)

Bookmark: GIS Shape Files to PostGIS
well001s (reader SHAPEFILE_1)
    attributes: SURFACE_ID long, SYMNUM long, API char(8), RELIAB char(2), LONG27 double, LAT27 double, LONG83 double, LAT83 double, WELLID char(5)
    -> BulkAttributeRenamer
BulkAttributeRenamer
    ATTRCHOICE = All Attributes
    CASE_CHANGE_TYPE = lower
    MODE_CHOICE = RENAME
    PATTERN_ACTION_DISP = CASECHANGE
    -> well_s (writer POSTGIS_1)
well_s (writer POSTGIS_1)
    attributes: surface_id int4, symnum int4, api varchar(8), reliab varchar(2), long27 float8, lat27 float8, long83 float8, lat83 float8, wellid varchar(5)
well001b (reader SHAPEFILE_2)
    attributes: BOTTOM_ID long, SURFACE_ID long, SYMNUM long, APINUM char(12), RELIAB char(2), API10 char(10), API char(8), LONG27 double, LAT27 double, LONG83 double, LAT83 double, OUT_FIPS char(1), CWELLNUM char(6), RADIOACT char(1), WELLID char(5), STCODE char(2)
    -> BulkAttributeRenamer_2
BulkAttributeRenamer_2
    ATTRCHOICE = All Attributes
    CASE_CHANGE_TYPE = lower
    MODE_CHOICE = RENAME
    PATTERN_ACTION_DISP = CASECHANGE
    -> well_b (writer POSTGIS_2)
well_b (writer POSTGIS_2)
    attributes: bottom_id int4, surface_id int4, symnum int4, apinum varchar(12), reliab varchar(2), api10 varchar(10), api varchar(8), long27 float8, lat27 float8, long83 float8, lat83 float8, out_fips varchar(1), cwellnum varchar(6), radioact varchar(1), wellid varchar(5), stcode varchar(2)
well001l (reader SHAPEFILE_3)
    attributes: BOTTOM_ID long, SURFACE_ID long, API10 char(10), API char(8), STCODE char(2)
    -> BulkAttributeRenamer_3
BulkAttributeRenamer_3
    ATTRCHOICE = All Attributes
    CASE_CHANGE_TYPE = lower
    MODE_CHOICE = RENAME
    PATTERN_ACTION_DISP = CASECHANGE
    -> well_l (writer POSTGIS_3)
well_l (writer POSTGIS_3)
    attributes: bottom_id int4, surface_id int4, api10 varchar(10), api varchar(8), stcode varchar(2)
