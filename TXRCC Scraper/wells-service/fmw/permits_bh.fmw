FME workspace permits_bh.fmw

Parameters:
- SourceDataset_POSTGIS = pg.whitestar.com   # Connection
- SourceDataset_POSTGIS_7 = pg.whitestar.com   # Connection
- DestDataset_POSTGIS = pg.whitestar.com   # Connection

Readers:
- POSTGIS_1: POSTGIS from $(SourceDataset_POSTGIS)
- POSTGIS_2: POSTGIS from $(SourceDataset_POSTGIS_7)

Writers:
- POSTGIS_3: POSTGIS to $(DestDataset_POSTGIS) in EPSG:4267

Note: Node - srf_lng and lat are NAD27!
SQLCreator
    DATASET = pg.whitestar.com
    EXPOSED_ATTRIBUTE_LIST = api,apinum,bottom_id,lat27,lat83,long27,long83,out_fips,radioactv,reliab,stcode,surface_id,symnum,well_num,wellid
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      api,
      apinum,
      bottom_id,
      cwellnum as well_num,
      lat27,
      lat83,
      long27,
      long83,
      out_fips,
      radioact as radioactv,
      reliab,
      stcode,
      surface_id,
      symnum,
      wellid
      from well_b
      order by surface_id
    RESULT -> Counter
Counter
    CNT_ATTR = uniqueno
    DOMAIN = counter
    SCOPE = Global
    START = 1
    -> AttributeCreator_2
AttributeCreator_2
    ATTR_TABLE:
      SET_TO api_state = 42
      SET_TO state = TX
      SET_TO footage_1
      SET_TO footage_2
      SET_TO updt_date = @DateTimeNow()
      SET_TO data_src = TXRRC
      SET_TO ftg_src = WS
    -> SubstringExtractor
Note: Extract API County Code
SubstringExtractor
    END = 2
    RESULT_ATTR = api_cnty
    SRC_STRING = @Value(api)
    START = 0
    -> CoordinateSystemSetter
CoordinateSystemSetter
    COORDSYS = EPSG:4267
    -> VertexCreator
VertexCreator
    MEASURE_TYPE = Discrete
    MODE_NAME = Replace with Point
    XVAL = @Value(long27)
    YVAL = @Value(lat27)
    -> PointOnAreaOverlayer [POINT]
tx_county_district (reader POSTGIS_2)
    attributes: state varchar(20), postal varchar(2), st_api varchar(2), st_census varchar(2), cty_api varchar(3), cty_census varchar(3), stcty_api varchar(5), stcty_census varchar(5), county varchar(60), amoddate timestamp, gmoddate timestamp, datum varchar(5), source varchar(10), rrdist varchar(2)
    -> PointOnAreaOverlayer [AREA]
PointOnAreaOverlayer
    ATTR_ACCUM_MODE = Prefix Incoming
    DEAGGREGATE_INPUT = Yes
    INCOMING_PREFIX = xx_
    OV_ATTR = _overlaps
    POLYS_FIRST = NO
    POINT -> Tester_4
Junction_8
    -> AttributeValueMapper
AttributeRenamer_5
    ATTR_TABLE:
      RENAME_SET_DEFAULT footage_1_dir > bh_ftg1dir
      RENAME_SET_DEFAULT footage_2_dir > bh_ftg2dir
      RENAME_SET_DEFAULT ABSNO > comments
      RENAME_SET_DEFAULT footage_1 > bh_ftg1
      RENAME_SET_DEFAULT footage_2 > bh_ftg2
      RENAME_SET_DEFAULT footage_1_dir > bh_ftg1dir
      RENAME_SET_DEFAULT footage_2_dir > bh_ftg2dir
      RENAME_SET_DEFAULT lat27 > bh_lat27
      RENAME_SET_DEFAULT long27 > bh_lng27
      RENAME_SET_DEFAULT lat83 > bh_lat83
      RENAME_SET_DEFAULT long83 > bh_lng83
      RENAME_SET_DEFAULT uniqueno > bh_num
    -> StringPadder_11
StringPadder_11
    BLANK_ATTRIBUTE = Yes
    PADCHAR = 0
    SIDE = Right
    SRC_ATTRS = wstar_id
    WIDTH = 14
    -> StringLengthCalculator_3
AttributeCreator_4
    ATTR_TABLE = SET_TO api = @Value(wstar_id)
    -> Sorter
Sorter
    SORT_PARM = api ALPHA ASCENDING bh_num NUMERIC ASCENDING
    SORTED -> tx_bottom_hole_latest_build (writer POSTGIS_3)
tx_bottom_hole_latest_build (writer POSTGIS_3)
    attributes: wstar_id varchar(14),BTree, api varchar(14),BTree, api_state int2, api_cnty int2,BTree, state varchar(2), county varchar(25),BTree, surface_id int4,BTree, bh_num int4, ftg_src char(2), bh_ftg1 int4, bh_ftg1dir varchar(5), bh_ftg2 int4, bh_ftg2dir varchar(5), bh_lat27 float8, bh_lng27 float8, bh_lat83 float8, bh_lng83 float8, post_code varchar(10), bh_abstrct varchar(60), bh_survno varchar(60), bh_survna varchar(60), bh_blockno varchar(60), bh_blockna varchar(60)

Bookmark: County code in API Number not match that in calculated point in polygon operation
Tester_4
    BOOL_OP = OR
    COMPOSITE_TEST = 1
    TEST_CLAUSE = TEST @Value(api_cnty) = @Value(xx_cty_api)
    TEST_MODE = TEST
    PASSED -> AttributeCopier_2
    FAILED -> AttributeCreator
Note: cty code mismatch
AttributeCreator
    ATTR_TABLE = SET_TO api_cty_mismatch_flag = T
    -> AttributeCopier_2
AttributeCopier_2
    ATTR_TABLE:
      COPY xx_cty_api > api_cnty
      COPY xx_county > county
      COPY xx_rrdist > rrdist
    -> BulkAttributeRemover
BulkAttributeRemover
    ATTR_EXP = xx_.*
    -> AttributeRemover
AttributeRemover
    REMOVE_ATTRS = _overlaps
    -> StringConcatenator_5

Bookmark: Calculate wstar_id and 10 digiti API Numbers. api and wstar_id are based on wellid if no API number present. 42 + county code + 5 + 08d format wellid
StringConcatenator_5
    ACTION = Create New Attribute
    PARM_LINE = fme_basicstring:17%11:@Value(api_state)@Value(api)
    VAL_ATTR = wstar_id
    -> StringLengthCalculator_2
StringLengthCalculator_2
    LENGTH_ATTR = _length
    SRC_ATTR = api
    -> TestFilter_3
TestFilter_3
    DEFAULT_VALUE = <UNFILTERED>
    TEST_LIST = "BOOL_OP,OR,COMPOSITE_TEST,""""""1"""""",TEST_CLAUSE,TEST @Value(_length) = 8",8,"BOOL_OP,OR,COMPOSITE_TEST,""""""1"""""",TEST_CLAUSE,TEST @Value(_length) = 3",3
    8 -> Junction_8
    3 -> StringFormatter_2
    <UNFILTERED> -> AttributeCreator_3
AttributeCreator_3
    ATTR_TABLE = SET_TO wstar_id = @Value(apinum)
    -> Junction_8
Note: Create 'API' based on 5 + 08d wellid
StringFormatter_2
    FORMAT = 08d
    SRC_ATTRS = surface_id
    -> StringConcatenator_4
StringConcatenator_4
    ACTION = Create New Attribute
    PARM_LINE = fme_basicstring:17%11%1%18:@Value(api_state)@Value(api)5@Value(surface_id)
    VAL_ATTR = wstar_id
    -> Junction_8

Bookmark: Calculate Block Survey Abstract
Note: Post Code lookup table
AttributeValueMapper
    DIRECTION = Forward (Source To Destination)
    LUT = 10,PB,103,STO,104,INJ,105,INJ,106,INJ,107,INJ,108,OB,109,OB,11,INJ,110,OB,111,OB,112,SRV,113,SRV,114,SRV,115,SRV,116,P&A,117,P&A,118,P&A,119,P&A,12,TEST,121,BW,122,BW,123,BW,124,INJ,125,INJ,126,INJ,127,INJ,128,OB,129,OB,13,DIRLOC,130,OB,131,OB,132,SRV,133,SRV,134,SRV,135,SRV,136,P&A,137,P&A,138,P&A,139,P&A,140,STO,141,STO,142,STO,143,STO,144,INJ,145,INJ,146,INJ,147,INJ,148,OB,149,OB,15,UNKN,150,OB,151,OB,152,P&A,153,P&A,154,P&A,155,P&A,16,TEST,17,OS,18,GS,19,SHUTIN-OIL,2,LOC,20,SHUTIN-GAS,21,INJ,22,INJ,23,INJ,24,DERRICK,3,DRY,36,GEO,4,OIL,5,GAS,6,O&G,7,PO,73,BW,74,H2O,75,WSO,76,WSG,77,WSB,78,OB,79,OB,8,PG,80,OB,81,OB,86,HORDH,87,STKWLOC,88,STO,89,SRV,9,ABDN,90,SRV,91,SRV,92,SRV
    SRC = symnum
    VAL_ATTR = post_code
    -> PointOnAreaOverlayer_2 [POINT]
TX_ABSTRACT (reader POSTGIS_1)
    attributes: objectid int4, POSTAL varchar(2), COUNTY varchar(60), CTY_API varchar(3), DISTRICT varchar(2), BLOCKNA varchar(60), BLOCKNO varchar(60), BLOOVNA varchar(60), BLOOVNO varchar(60), SURVNA varchar(60), SURVNO varchar(60), SUROVNA varchar(60), SUROVNO varchar(60), ABSNA varchar(60), ABSNO varchar(60), ABSOVNA varchar(60), ABSOVNO varchar(60), SUBDNA varchar(60), SUBDNO varchar(60), LOTNA varchar(60), LOTNO varchar(60), TRACTNA varchar(60), TRACTNO varchar(60), AMODDATE date, GMODDATE date, DATUM varchar(5), SOURCE varchar(10)
    -> PointOnAreaOverlayer_2 [AREA]
PointOnAreaOverlayer_2
    ATTR_ACCUM_MODE = Merge Incoming
    ATTR_CONFLICT_RES = Use Original
    DEAGGREGATE_INPUT = Yes
    OV_ATTR = _overlaps
    POLYS_FIRST = NO
    POINT -> AttributeRenamer
    AREA -> EsriReprojector_2
AttributeRenamer
    ATTR_TABLE:
      RENAME_SET_DEFAULT BLOCKNA > bh_blockna
      RENAME_SET_DEFAULT SURVNA > bh_survna
      RENAME_SET_DEFAULT SURVNO > bh_survno
      RENAME_SET_DEFAULT BLOCKNO > bh_blockno
      RENAME_SET_DEFAULT ABSNO > bh_abstrct
    -> EsriReprojector

Bookmark: Reverse Geocoder
EsriReprojector
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> NeighborPairFinder_2 [BASE]
EsriReprojector_2
    DEST = ESRIWKT|NAD_1927_StatePlane_Texas_Central_FIPS_4203|PROJCS["NAD_1927_StatePlane_Texas_Central_FIPS_4203",GEOGCS["GCS_North_American_1927",DATUM["D_North_American_1927",SPHEROID["Clarke_1866",6378206.4,294.9786982]],PRIMEM["Greenwich",0.0],UNIT["Degree",0.0174532925199433]],PROJECTION["Lambert_Conformal_Conic"],PARAMETER["False_Easting",2000000.0],PARAMETER["False_Northing",0.0],PARAMETER["Central_Meridian",-100.3333333333333],PARAMETER["Standard_Parallel_1",30.11666666666667],PARAMETER["Standard_Parallel_2",31.88333333333333],PARAMETER["Latitude_Of_Origin",29.66666666666667],UNIT["Foot_US",0.3048006096012192]]
    GEOTRANSFORMATION_DIRECTION = Forward
    INTERPOLATION_TYPE_NAME = Nearest Neighbor
    RASTER_CELL_SIZE = Preserve Cells
    RASTER_TOLERANCE = 0.0
    SOURCE = ESRIWKT|GCS_North_American_1927|GEOGCS["GCS_North_American_1927",DATUM["D_North_American_1927",SPHEROID["Clarke_1866",6378206.4,294.9786982]],PRIMEM["Greenwich",0.0],UNIT["Degree",0.0174532925199433]]
    REPROJECTED -> NeighborPairFinder_2 [CANDIDATE]
NeighborPairFinder_2
    KEYATTR = ABSNO
    MAX = 30000
    MINANGLE = 70
    MODE = Bases and Candidates
    MATCHED -> TestFilter
TestFilter
    DEFAULT_VALUE = <UNFILTERED>
    TEST_LIST:
      "BOOL_OP,OR,COMPOSITE_TEST,""""""1 OR 2"""""",TEST_CLAUSE,TEST @Value(_heading1) > 337.5
      TEST @Value(_heading1) <= 22.5",FEL,"BOOL_OP,AND,COMPOSITE_TEST,""""""1 AND 2"""""",TEST_CLAUSE,TEST @Value(_heading1) > 22.5
      TEST @Value(_heading1) <= 67.5",FNEL,"BOOL_OP,AND,COMPOSITE_TEST,""""""1 AND 2"""""",TEST_CLAUSE,TEST @Value(_heading1) > 67.5
      TEST @Value(_heading1) <= 112.5",FNL,"BOOL_OP,AND,COMPOSITE_TEST,""""""1 AND 2"""""",TEST_CLAUSE,TEST @Value(_heading1) > 112.5
      TEST @Value(_heading1) <= 157.5",FNWL,"BOOL_OP,AND,COMPOSITE_TEST,""""""1 AND 2"""""",TEST_CLAUSE,TEST @Value(_heading1) > 157.5
      TEST @Value(_heading1) <= 202.5",FWL,"BOOL_OP,AND,COMPOSITE_TEST,""""""1 AND 2"""""",TEST_CLAUSE,TEST @Value(_heading1) > 202.5
      TEST @Value(_heading1) <= 247.5",FSWL,"BOOL_OP,AND,COMPOSITE_TEST,""""""1 AND 2"""""",TEST_CLAUSE,TEST @Value(_heading1) > 247.5
      TEST @Value(_heading1) <= 292.5",FSL,"BOOL_OP,AND,COMPOSITE_TEST,""""""1 AND 2"""""",TEST_CLAUSE,TEST @Value(_heading1) > 292.5
      TEST @Value(_heading1) <= 337.5",FSEL
    FEL -> AttributeCreator_22
    FNEL -> AttributeCreator_34
    FNL -> AttributeCreator_24
    FNWL -> AttributeCreator_33
    FWL -> AttributeCreator_25
    FSWL -> AttributeCreator_32
    FSL -> AttributeCreator_26
    FSEL -> AttributeCreator_31
    <UNFILTERED> -> AttributeCreator_23
AttributeCreator_22
    ATTR_TABLE = SET_TO footage_1_dir = FEL
    -> TestFilter_2
AttributeCreator_34
    ATTR_TABLE = SET_TO footage_1_dir = FNEL
    -> TestFilter_2
AttributeCreator_24
    ATTR_TABLE = SET_TO footage_1_dir = FNL
    -> TestFilter_2
AttributeCreator_33
    ATTR_TABLE = SET_TO footage_1_dir = FNWL
    -> TestFilter_2
AttributeCreator_25
    ATTR_TABLE = SET_TO footage_1_dir = FWL
    -> TestFilter_2
AttributeCreator_32
    ATTR_TABLE = SET_TO footage_1_dir = FSWL
    -> TestFilter_2
AttributeCreator_26
    ATTR_TABLE = SET_TO footage_1_dir = FSL
    -> TestFilter_2
AttributeCreator_31
    ATTR_TABLE = SET_TO footage_1_dir = FSEL
    -> TestFilter_2
TestFilter_2
    DEFAULT_VALUE = <UNFILTERED>
    TEST_LIST:
      "BOOL_OP,OR,COMPOSITE_TEST,""""""1 OR 2"""""",TEST_CLAUSE,TEST @Value(_heading2) > 337.5
      TEST @Value(_heading2) <= 22.5",FEL,"BOOL_OP,AND,COMPOSITE_TEST,""""""1 AND 2"""""",TEST_CLAUSE,TEST @Value(_heading2) > 22.5
      TEST @Value(_heading2) <= 67.5",FNEL,"BOOL_OP,AND,COMPOSITE_TEST,""""""1 AND 2"""""",TEST_CLAUSE,TEST @Value(_heading2) > 67.5
      TEST @Value(_heading2) <= 112.5",FNL,"BOOL_OP,AND,COMPOSITE_TEST,""""""1 AND 2"""""",TEST_CLAUSE,TEST @Value(_heading2) > 112.5
      TEST @Value(_heading2) <= 157.5",FNWL,"BOOL_OP,AND,COMPOSITE_TEST,""""""1 AND 2"""""",TEST_CLAUSE,TEST @Value(_heading2) > 157.5
      TEST @Value(_heading2) <= 202.5",FWL,"BOOL_OP,AND,COMPOSITE_TEST,""""""1 AND 2"""""",TEST_CLAUSE,TEST @Value(_heading2) > 202.5
      TEST @Value(_heading2) <= 247.5",FSWL,"BOOL_OP,AND,COMPOSITE_TEST,""""""1 AND 2"""""",TEST_CLAUSE,TEST @Value(_heading2) > 247.5
      TEST @Value(_heading2) <= 292.5",FSL,"BOOL_OP,AND,COMPOSITE_TEST,""""""1 AND 2"""""",TEST_CLAUSE,TEST @Value(_heading2) > 292.5
      TEST @Value(_heading2) <= 337.5",FSEL
    FEL -> AttributeCreator_38
    FNEL -> AttributeCreator_37
    FNL -> AttributeCreator_36
    FNWL -> AttributeCreator_35
    FWL -> AttributeCreator_30
    FSWL -> AttributeCreator_29
    FSL -> AttributeCreator_28
    FSEL -> AttributeCreator_27
    <UNFILTERED> -> AttributeCreator_23
AttributeCreator_38
    ATTR_TABLE = SET_TO footage_2_dir = FEL
    -> AttributeCreator_23
AttributeCreator_37
    ATTR_TABLE = SET_TO footage_2_dir = FNEL
    -> AttributeCreator_23
AttributeCreator_36
    ATTR_TABLE = SET_TO footage_2_dir = FNL
    -> AttributeCreator_23
AttributeCreator_35
    ATTR_TABLE = SET_TO footage_2_dir = FNWL
    -> AttributeCreator_23
AttributeCreator_30
    ATTR_TABLE = SET_TO footage_2_dir = FWL
    -> AttributeCreator_23
AttributeCreator_29
    ATTR_TABLE = SET_TO footage_2_dir = FSWL
    -> AttributeCreator_23
AttributeCreator_28
    ATTR_TABLE = SET_TO footage_2_dir = FSL
    -> AttributeCreator_23
AttributeCreator_27
    ATTR_TABLE = SET_TO footage_2_dir = FSEL
    -> AttributeCreator_23
AttributeCreator_23
    ATTR_TABLE:
      SET_TO ftg_src = WS
      SET_TO footage_1 = @Value(_distance1)
      SET_TO footage_2 = @Value(_distance2)
    -> AttributeRounder
AttributeRounder
    PLACES = 0
    ROUND_TYPE = Nearest
    SRC_ATTRS = footage_1 _distance2 _distance1 footage_2
    -> AttributeRenamer_5

Bookmark: wstar_id Check/Correct
StringLengthCalculator_3
    LENGTH_ATTR = _length_wstar_id
    SRC_ATTR = wstar_id
    -> Tester_2
Tester_2
    BOOL_OP = OR
    COMPOSITE_TEST = 1
    TEST_CLAUSE = TEST @Value(_length_wstar_id) < 14
    TEST_MODE = TEST
    PASSED -> StringPadder_3
    FAILED -> AttributeCreator_4
StringPadder_3
    BLANK_ATTRIBUTE = Yes
    PADCHAR = 0
    SIDE = Right
    SRC_ATTRS = wstar_id
    WIDTH = 14
    <REJECTED> -> AttributeCreator_4
