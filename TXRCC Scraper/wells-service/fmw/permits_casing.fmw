FME workspace permits_casing.fmw

Parameters:
- DestDataset_POSTGIS_7 = pg.whitestar.com   # Connection

Writers:
- POSTGIS_1: POSTGIS to $(DestDataset_POSTGIS_7) in LL27

SQLCreator_2
    COORDSYS = LL27
    DATASET = pg.whitestar.com
    EXPOSED_ATTRIBUTE_LIST = api,api_cnty,api_state,county,state,wstar_id
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select *
      from tx_header_pre_cum
      where length(api) = 8
    RESULT -> FeatureJoiner [LEFT]
SQLCreator
    DATASET = pg.whitestar.com
    EXPOSED_ATTRIBUTE_LIST = api,casing_cnt,cmt_amt,cmt_msmt,csg_amtlft,csg_frcdnm,csg_frcnum,csg_inches,csg_tp_cmt,csg_weight,depth_set,hole_frc_d,hole_frc_n,hole_inch,mstg_dpth
    FORMAT = POSTGRES
    POSTGRES_CREATE_FEATURE_TABLES_FROM_DATA = Yes
    POSTGRES_NAMED_CONNECTION = pg.whitestar.com
    POSTGRES_QUERY_FEATURE_TYPES_FOR_MERGE_FILTERS = Yes
    POSTGRES_READ_TIME_WITH_TIMEZONE = Yes
    SQL_STATEMENT:
      select distinct
      wb_api as api,
      wb_casing_count as casing_cnt,
      wb_casing_depth_set as depth_set,
      wb_amount_of_cement as cmt_amt,
      wb_cement_measurement as cmt_msmt,
      wb_cas_inch as csg_inches,
      wb_cas_fracnum as csg_frcnum,
      wb_case_fracdenom as csg_frcdnm,
      wb_hole_frac_num as hole_frc_n,
      wb_hole_frac_denom as hole_frc_d,
      wb_cas_wt_table as csg_weight,
      wb_mlti_stg_tool_dpth as mstg_dpth,
      wb_hole_inch as hole_inch,
      wb_top_of_cement_casing as csg_tp_cmt,
      wb_amount_casing_left as csg_amtlft
      from wb06
    RESULT -> FeatureJoiner [RIGHT]
FeatureJoiner
    ATTR_CONFLICT_RES = Use Left
    GEOMETRY_HANDLING = Use Left
    JOIN_KEYS = api api AUTO
    JOIN_MODE = Inner
    JOINED -> StringLengthCalculator_3
AttributeCreator_4
    ATTR_TABLE = SET_TO api = @Value(wstar_id)
    -> Sorter
Sorter
    SORT_PARM = api ALPHA ASCENDING casing_cnt NUMERIC ASCENDING
    SORTED -> tx_casings_latest_build (writer POSTGIS_1)
tx_casings_latest_build (writer POSTGIS_1)
    attributes: wstar_id varchar(14),BTree, api varchar(14),BTree, api_state int2, api_cnty int2,BTree, state varchar(2), county varchar(25),BTree, casing_cnt int2, csg_inches int2, csg_tp_cmt varchar(7), csg_amtlft varchar(5), depth_set int4, mstg_dpth int4, cmt_amt int4, cmt_msmt char(1), csg_weight varchar(8), csg_frcnum int2, csg_frcdnm int2, hole_frc_n int2, hole_frc_d int2, hole_inch int2

Bookmark: wstar_id Check/Correct
StringLengthCalculator_3
    LENGTH_ATTR = _length_wstar_id
    SRC_ATTR = wstar_id
    -> Tester_2
Tester_2
    BOOL_OP = OR
    COMPOSITE_TEST = 1
    TEST_CLAUSE = TEST @Value(_length_wstar_id) < 14
    TEST_MODE = TEST
    PASSED -> StringPadder_3
    FAILED -> AttributeCreator_4
StringPadder_3
    BLANK_ATTRIBUTE = Yes
    PADCHAR = 0
    SIDE = Right
    SRC_ATTRS = wstar_id
    WIDTH = 14
    <REJECTED> -> AttributeCreator_4
