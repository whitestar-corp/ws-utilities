FME workspace pp_permits.fmw

Parameters:
- DestDataset_POSTGRES = pg.whitestar.com   # Connection
- SourceDataset_CSV2 = D:\Users\rwhite\Documents\texas-wells\wells-service\data\drilling-permit\perm02.csv   # Source CSV (Comma Separated Value) File(s)

Readers:
- CSV2_1: CSV2 from $(SourceDataset_CSV2)

Writers:
- POSTGRES_1: POSTGRES to $(DestDataset_POSTGRES)

CSV (reader CSV2_1)
    attributes: da_permit_number string, da_permit_sequence_number string, da_permit_county_code string, da_permit_lease_name string, da_permit_district string, da_permit_well_number string, da_permit_total_depth string, da_permit_operator_number string, da_type_application string, da_other_explanation string, da_address_unique_number string, da_zip_code_prefix string, da_zip_code_suffix string, da_fiche_set_number string, da_onshore_county string, da_received_date string, da_permit_issued_date string, da_permit_amended_date string, da_permit_extended_date string, da_permit_spud_date string, da_permit_surface_casing_date string, da_well_status string, da_permit_well_status_date string, da_permit_expired_date string, da_permit_cancelled_date string, da_cancellation_reason string, da_p12_filed_flag string, da_substandard_acreage_flag string, da_rule_36_flag string, da_h9_flag string,
      da_rule_37_case_number string, da_rule_38_docket_number string, da_location_formation_flag string, da_old_location string, da_surface_section string, da_surface_block string, da_surface_survey string, da_surface_abstract string, da_surface_acres string, da_surface_miles_from_city string, da_surface_direction_from_city string, da_surface_nearest_city string, da_surface_lease_feet_1 string, da_surface_lease_direction_1 string, da_surface_lease_feet_2 string, da_surface_lease_direction_2 string, da_old_surface_lease_distance string, da_surface_survey_feet_1 string, da_surface_survey_direction_1 string, da_surface_survey_feet_2 string, da_surface_survey_direction_2 string, da_old_survey_distance string, da_nearest_well string, da_nearest_well_feet string, da_nearest_well_direction string, da_nearest_well_format string, da_final_update string, da_cancelled_flag string, da_spud_in_flag string, da_directional_well_flag string,
      da_sidetrack_well_flag string, da_moved_indicator string, da_permit_conv_issued_date string, da_rule_37_granted_code string, da_horizontal_well_flag string, da_duplicate_permit_flag string, da_nearest_lease_line string, api_number string
    -> perm02 (writer POSTGRES_1)
perm02 (writer POSTGRES_1)
    attributes: da_permit_number int4,BTree, da_permit_sequence_number int2, da_permit_county_code int2, da_permit_lease_name varchar(32), da_permit_district int2, da_permit_well_number varchar(6), da_permit_total_depth int4, da_permit_operator_number int4, da_type_application char(2), da_other_explanation varchar(30), da_address_unique_number int4, da_zip_code_prefix int4, da_zip_code_suffix int4, da_fiche_set_number int4, da_onshore_county int2, da_received_date date, da_permit_issued_date date, da_permit_amended_date date, da_permit_extended_date date, da_permit_spud_date date, da_permit_surface_casing_date date, da_well_status char(1), da_permit_well_status_date date, da_permit_expired_date date, da_permit_cancelled_date date, da_cancellation_reason varchar(30), da_p12_filed_flag char(1), da_substandard_acreage_flag char(1), da_rule_36_flag char(1), da_h9_flag char(1),
      da_rule_37_case_number varchar(7), da_rule_38_docket_number varchar(7), da_location_formation_flag char(1), da_old_location varchar(52), da_surface_section varchar(8), da_surface_block varchar(10), da_surface_survey varchar(55), da_surface_abstract varchar(6), da_surface_acres float4, da_surface_miles_from_city float4, da_surface_direction_from_city varchar(6), da_surface_nearest_city varchar(13), da_surface_lease_feet_1 float4, da_surface_lease_direction_1 varchar(16), da_surface_lease_feet_2 float4, da_surface_lease_direction_2 varchar(16), da_old_surface_lease_distance varchar(28), da_surface_survey_feet_1 float4, da_surface_survey_direction_1 varchar(13), da_surface_survey_feet_2 float4, da_surface_survey_direction_2 varchar(13), da_old_survey_distance varchar(28), da_nearest_well varchar(28), da_nearest_well_feet float4, da_nearest_well_direction varchar(13), da_nearest_well_format char(1), da_final_update date, da_cancelled_flag char(1), da_spud_in_flag char(1), da_directional_well_flag char(1),
      da_sidetrack_well_flag char(1), da_moved_indicator char(1), da_permit_conv_issued_date date, da_rule_37_granted_code char(1), da_horizontal_well_flag char(1), da_duplicate_permit_flag char(1), da_nearest_lease_line char(7), api_number varchar(8),BTree
