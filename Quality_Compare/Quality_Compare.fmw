FME workspace Quality_Compare.fmw

Parameters:
- SourceDataset_POSTGIS = pg.whitestar.com   # Connection
- Current_Year = 2020   # Current Year
- Current_Quarter = q4
- Previous_Quarter = PREVIOUS_QUARTER   # Previous Quarter
- Previous_Year = PREVIOUS_YEAR   # Previous Year

Readers:
- POSTGIS_1: POSTGIS from $(SourceDataset_POSTGIS)
- POSTGIS_2: POSTGIS from $(SourceDataset_POSTGIS)

(no name)
SQLCreator_AllTables
    DATASET = pg.whitestar.com
    EXPOSED_ATTRIBUTE_LIST = table_name
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT = SELECT table_name FROM information_schema.tables WHERE (table_schema = 'public' AND table_name LIKE 'WS_Parcel%')
FeatureMerger_CurrentPolys
    ATTR_ACCUM_MODE = Merge Supplier
    ATTR_CONFLICT_RES = Use Requestor
    IGNORE_NULLS = No
    JOIN_KEYS = @Value(target_polys_current) @Value(table_name) AUTO
    MERGE_TYPE = Attributes Only
    PROCESS_DUPS = NO
    REJECT_NULL_MISSING_KEYS = No
    SUPPLIERS_FIRST = No
FeatureMerger_PreviousPolys
    ATTR_ACCUM_MODE = Merge Supplier
    ATTR_CONFLICT_RES = Use Requestor
    IGNORE_NULLS = No
    JOIN_KEYS = @Value(target_polys_previous) @Value(table_name) AUTO
    MERGE_TYPE = Attributes Only
    PROCESS_DUPS = NO
    REJECT_NULL_MISSING_KEYS = No
    SUPPLIERS_FIRST = No
FeatureMerger_CurrentPoints
    ATTR_ACCUM_MODE = Merge Supplier
    ATTR_CONFLICT_RES = Use Requestor
    IGNORE_NULLS = No
    JOIN_KEYS = @Value(target_points_current) @Value(table_name) AUTO
    MERGE_TYPE = Attributes Only
    PROCESS_DUPS = NO
    REJECT_NULL_MISSING_KEYS = No
    SUPPLIERS_FIRST = No
FeatureMerger_PreviousPoints_2
    ATTR_ACCUM_MODE = Merge Supplier
    ATTR_CONFLICT_RES = Use Requestor
    IGNORE_NULLS = No
    JOIN_KEYS = @Value(target_points_previous) @Value(table_name) AUTO
    MERGE_TYPE = Attributes Only
    PROCESS_DUPS = NO
    REJECT_NULL_MISSING_KEYS = No
    SUPPLIERS_FIRST = No
AttributeManager_5
    ATTR_TABLE = SET_TO Current_Polys_Exist = 1
AttributeManager_6
    ATTR_TABLE = SET_TO Current_Polys_Exist = 0
AttributeManager_2
    ATTR_TABLE = SET_TO Previous_Polys_Exist = 1
AttributeManager_7
    ATTR_TABLE = SET_TO Previous_Polys_Exist = 0
AttributeManager_3
    ATTR_TABLE = SET_TO Current_Points_Exist = 1
AttributeManager_4
    ATTR_TABLE = SET_TO Current_Points_Exist = 0
AttributeManager_8
    ATTR_TABLE = SET_TO Previous_Points_Exist = 1
AttributeManager_9
    ATTR_TABLE = SET_TO Previous_Points_Exist = 0
Junction_3
Junction
Junction_4
TestFilter
    DEFAULT_VALUE = <UNFILTERED>
    TEST_LIST:
      "BOOL_OP,AND,COMPOSITE_TEST,""""""<Unused>"""""",TEST_CLAUSE,TEST @Value(Current_Polys_Exist) = 1
      TEST @Value(Previous_Polys_Exist) = 1
      TEST @Value(Current_Points_Exist) = 1
      TEST @Value(Previous_Points_Exist) = 1",All_Exist,"BOOL_OP,AND,COMPOSITE_TEST,""""""<Unused>"""""",TEST_CLAUSE,TEST @Value(Current_Polys_Exist) = 0
      TEST @Value(Previous_Polys_Exist) = 0
      TEST @Value(Current_Points_Exist) = 1
      TEST @Value(Previous_Points_Exist) = 1",Points_Only,"BOOL_OP,AND,COMPOSITE_TEST,""""""<Unused>"""""",TEST_CLAUSE,TEST @Value(Current_Polys_Exist) = 1
      TEST @Value(Previous_Polys_Exist) = 1
      TEST @Value(Current_Points_Exist) = 0
      TEST @Value(Previous_Points_Exist) = 0",Polys_Only,"BOOL_OP,AND,COMPOSITE_TEST,""""""<Unused>"""""",TEST_CLAUSE,TEST @Value(Current_Polys_Exist) = 1
      TEST @Value(Previous_Polys_Exist) = 0
      TEST @Value(Current_Points_Exist) = 1
      TEST @Value(Previous_Points_Exist) = 0",Current_Only,"BOOL_OP,AND,COMPOSITE_TEST,""""""<Unused>"""""",TEST_CLAUSE,TEST @Value(Current_Polys_Exist) = 1
      TEST @Value(Previous_Polys_Exist) = 0
      TEST @Value(Current_Points_Exist) = 1
      TEST @Value(Previous_Points_Exist) = 1",No_Previous_Polys
Junction_2
Junction_10
Junction_9
Junction_8
Junction_7
Junction_6
Sampler_6
    RATE = 2
    SAMPLE_MODE = No
    SAMPLE_TYPE_LONG = First N Features
Sampler_3
    RATE = 2
    SAMPLE_MODE = No
    SAMPLE_TYPE_LONG = First N Features
Sampler_2
    RATE = 2
    SAMPLE_MODE = No
    SAMPLE_TYPE_LONG = First N Features
Sampler_5
    RATE = 2
    SAMPLE_MODE = No
    SAMPLE_TYPE_LONG = First N Features
Sampler_4
    RATE = 2
    SAMPLE_MODE = No
    SAMPLE_TYPE_LONG = First N Features
SQLExecutor_All_Exist
    COMBINE_ATTRS = Result Attributes Only
    COMBINE_GEOM = Initiator Geometry Only
    DATASET = pg.whitestar.com
    EXPOSED_ATTRIBUTE_LIST = FIPS,"Prv Pnt Cnt","Cur Pnt Cnt","Prv Poly Cnt","Cur Poly Cnt","Prv Pnt Qual","Cur Pnt Qual","Prv Poly Qual","Cur Poly Qual",AMOD,GMOD
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      (select max(fips) from  "@Value(target_points_current)") as "FIPS",

      (select count(*) from "@Value(target_points_previous)") as "Prv Pnt Cnt",
      (select count(*) from "@Value(target_points_current)") as "Cur Pnt Cnt",

      (with x as (select count(*) rcnt from "@Value(target_points_previous)" where pointloc = 'In Parcel'),
       y as (select count(*) scnt from  "@Value(target_points_previous)")
      select 100*rcnt/scnt from x, y) "Prv Pnt Qual",

      (with x as (select count(*) rcnt from "@Value(target_points_current)" where pointloc = 'In Parcel'),
       y as (select count(*) scnt from  "@Value(target_points_current)")
      select 100*rcnt/scnt from x, y) "Cur Pnt Qual",
        (select count(*) from "@Value(target_polys_previous)") as "Prv Poly Cnt",
        (select count(*) from "@Value(target_polys_current)") as "Cur Poly Cnt",

        (with x as (select count(*) rcnt from "@Value(target_polys_previous)" where pointloc = 'In Parcel'),
         y as (select count(*) scnt from "@Value(target_polys_previous)")
        select 100*rcnt/scnt from x, y) "Prv Poly Qual",
        (with x as (select count(*) rcnt from  "@Value(target_polys_current)" where pointloc = 'In Parcel'),
         y as (select count(*) scnt from "@Value(target_polys_current)")
        select 100*rcnt/scnt from x, y) "Cur Poly Qual",

      (select max(amoddate) from "@Value(target_points_current)") as "AMOD",
      (select max(gmoddate) from "@Value(target_points_current)") as "GMOD";
SQLExecutor_Points_Only
    COMBINE_ATTRS = Result Attributes Only
    COMBINE_GEOM = Initiator Geometry Only
    DATASET = pg.whitestar.com
    EXPOSED_ATTRIBUTE_LIST = FIPS,"Prv Pnt Cnt","Cur Pnt Cnt","Prv Poly Cnt","Cur Poly Cnt","Prv Pnt Qual","Cur Pnt Qual","Prv Poly Qual","Cur Poly Qual",AMOD,GMOD
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      (select max(fips) from  "@Value(target_points_current)") as "FIPS",

      (select count(*) from "@Value(target_points_previous)") as "Prv Pnt Cnt",
      (select count(*) from "@Value(target_points_current)") as "Cur Pnt Cnt",

      (with x as (select count(*) rcnt from "@Value(target_points_previous)" where pointloc = 'In Parcel'),
      y as (select count(*) scnt from  "@Value(target_points_previous)")
      select 100*rcnt/scnt from x, y) "Prv Pnt Qual",

      (with x as (select count(*) rcnt from "@Value(target_points_current)" where pointloc = 'In Parcel'),
      y as (select count(*) scnt from  "@Value(target_points_current)")
      select 100*rcnt/scnt from x, y) "Cur Pnt Qual",

      (select max(amoddate) from "@Value(target_points_current)") as "AMOD";
SQLExecutor_Polys_Only
    COMBINE_ATTRS = Result Attributes Only
    COMBINE_GEOM = Initiator Geometry Only
    DATASET = pg.whitestar.com
    EXPOSED_ATTRIBUTE_LIST = FIPS,"Prv Pnt Cnt","Cur Pnt Cnt","Prv Poly Cnt","Cur Poly Cnt","Prv Pnt Qual","Cur Pnt Qual","Prv Poly Qual","Cur Poly Qual",AMOD,GMOD
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      (select max(fips) from  "@Value(target_polys_current)") as "FIPS",

      (select count(*) from "@Value(target_polys_previous)") as "Prev Pnt Cnt",
      (select count(*) from "@Value(target_polys_current)") as "Cur Pnt  Cnt",

      (with x as (select count(*) rcnt from " @Value(target_polys_previous)" where pointloc = 'In Parcel'),
      y as (select count(*) scnt from  "@Value(target_polys_previous)")
      select 100*rcnt/scnt from x, y) "Prv Pnt Qual",

      (with x as (select count(*) rcnt from "@Value(target_polys_current)" where pointloc = 'In Parcel'),
      y as (select count(*) scnt from  "@Value(target_polys_current)")
      select 100*rcnt/scnt from x, y) "Cur Pnt Qual",

      (select max(gmoddate) from "@Value(target_polys_current)") as "GMOD";
SQLExecutor_Current_Only_2
    COMBINE_ATTRS = Result Attributes Only
    COMBINE_GEOM = Initiator Geometry Only
    DATASET = pg.whitestar.com
    EXPOSED_ATTRIBUTE_LIST = FIPS,"Prv Pnt Cnt","Cur Pnt Cnt","Prv Poly Cnt","Cur Poly Cnt","Prv Pnt Qual","Cur Pnt Qual","Prv Poly Qual","Cur Poly Qual",AMOD,GMOD
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      (select max(fips) from  "@Value(target_points_current)") as "FIPS",

      (select count(*) from "@Value(target_points_current)") as "Cur Pnt Cnt",

      (with x as (select count(*) rcnt from "@Value(target_points_current)" where pointloc = 'In Parcel'),
      y as (select count(*) scnt from  "@Value(target_points_current)")
      select 100*rcnt/scnt from x, y) "Cur Pnt Qual",

      (select count(*) from "@Value(target_polys_current)") as "Cur Poly Cnt",

      (with x as (select count(*) rcnt from "@Value(target_polys_current)" where pointloc = 'In Parcel'),
      y as (select count(*) scnt from  "@Value(target_polys_current)")
      select 100*rcnt/scnt from x, y)  "Cur Poly Qual",

      (select max(amoddate) from "@Value(target_points_current)") as "AMOD",
      (select max(gmoddate) from "@Value(target_points_current)") as "GMOD";
SQLExecutor_No_Prev_Polys
    COMBINE_ATTRS = Result Attributes Only
    COMBINE_GEOM = Initiator Geometry Only
    DATASET = pg.whitestar.com
    EXPOSED_ATTRIBUTE_LIST = FIPS,"Prv Pnt Cnt","Cur Pnt Cnt","Prv Poly Cnt","Cur Poly Cnt","Prv Pnt Qual","Cur Pnt Qual","Prv Poly Qual","Cur Poly Qual",AMOD,GMOD
    FORMAT = POSTGIS
    POSTGIS_CREATE_FEATURE_TABLES_FROM_DATA = Yes
    POSTGIS_DISABLE_COLLECTION_SPLITTING = yes
    POSTGIS_NAMED_CONNECTION = pg.whitestar.com
    POSTGIS_QUERY_FEATURE_TYPES_FOR_MERGE_FILTERS = Yes
    POSTGIS_READ_TIME_WITH_TIMEZONE = Yes
    POSTGIS_USE_TRUE_POSTGIS_TYPES = yes
    SQL_STATEMENT:
      select
      (select max(fips) from  "@Value(target_points_current)") as "FIPS",

      (select count(*) from "@Value(target_points_previous)") as "Prv Pnt Cnt",
      (select count(*) from "@Value(target_points_current)") as "Cur Pnt Cnt",

      (with x as (select count(*) rcnt from "@Value(target_points_previous)" where pointloc = 'In Parcel'),
       y as (select count(*) scnt from  "@Value(target_points_previous)")
      select 100*rcnt/scnt from x, y) "Prv Pnt Qual",

      (with x as (select count(*) rcnt from "@Value(target_points_current)" where pointloc = 'In Parcel'),
       y as (select count(*) scnt from  "@Value(target_points_current)")
      select 100*rcnt/scnt from x, y) "Cur Pnt Qual",
        (select count(*) from "@Value(target_polys_current)") as "Cur Poly Cnt",

      (with x as (select count(*) rcnt from  "@Value(target_polys_current)" where pointloc = 'In Parcel'),
         y as (select count(*) scnt from "@Value(target_polys_current)")
        select 100*rcnt/scnt from x, y) "Cur Poly Qual",

      (select max(amoddate) from "@Value(target_points_current)") as "AMOD",
      (select max(gmoddate) from "@Value(target_points_current)") as "GMOD";
Junction_5

Bookmark: Generate Name Template
parcel_lookup (reader POSTGIS_2)
    attributes: fips_code varchar(200), standard_polygons varchar(200), standard_points varchar(200), pro_polygons varchar(200), pro_points varchar(200)
TestFilter_ProPoints
    DEFAULT_VALUE = <UNFILTERED>
    TEST_LIST = "BOOL_OP,OR,COMPOSITE_TEST,""""""<Unused>"""""",TEST_CLAUSE,TEST pro_points NOT_ATTRIBUTE_VALUE_NULL """,Pro_Points
DuplicateFilter
    INPUT_ORDERED_CHOICE = No
    KEYATTR = fips_code
TestFilter_ProPolys
    DEFAULT_VALUE = <UNFILTERED>
    TEST_LIST = "BOOL_OP,OR,COMPOSITE_TEST,""""""<Unused>"""""",TEST_CLAUSE,TEST pro_polygons NOT_ATTRIBUTE_VALUE_NULL """,Pro_Polys
PythonCaller_BuildNameTemplate
    NEW_ATTRIBUTES = name_template target_polys_current target_points_current previous_points_SQL previous_polys_SQL sql_template
    PYTHONSOURCE:
      import fme
      import fmeobjects

      def processFeature(feature):

          root_table = feature.getAttribute("pro_polygons")

          if(len(root_table.split("_")) < 4):
              root_table = feature.getAttribute("pro_points")

          splits = root_table.split("_")
          length = len(splits)

          template_string_parts =  []
          template_string_parts.append("WS")
          template_string_parts.append("Parcel-POINTS_OR_POLYS-")

          for i in range(2, length - 3):
              template_string_parts.append(splits[i])

          sql_template = "_".join(template_string_parts)

          template_string_parts.append("-YEAR-")
          template_string_parts.append("pro")
          template_string_parts.append( "-QUARTER-")
          name_template = "_".join(template_string_parts)

          Q = FME_MacroValues['Current_Quarter']
          #Q0 = FME_MacroValues['Previous_Quarter']

          Year = FME_MacroValues['Current_Year']
          #Year0 = FME_MacroValues['Previous_Year']

          feature.setAttribute("name_template", name_template)
          feature.setAttribute("sql_template", sql_template)

          target_poly_current = name_template.replace("-YEAR-", Year)
          target_poly_current = target_poly_current.replace("-POINTS_OR_POLYS-", "Polys")
          target_poly_current = target_poly_current.replace("-QUARTER-", Q)

          #target_poly_previous = name_template.replace("-YEAR-", Year0)
          #target_poly_previous = target_poly_previous.replace("-POINTS_OR_POLYS-", "Polys")
          #target_poly_previous = target_poly_previous.replace("-QUARTER-", Q0)

          target_points_current = name_template.replace("-YEAR-", Year)
          target_points_current = target_points_current.replace("-POINTS_OR_POLYS-", "Points")
          target_points_current = target_points_current.replace("-QUARTER-", Q)

          #target_points_previous = name_template.replace("-YEAR-", Year0)
          #target_points_previous = target_points_previous.replace("-POINTS_OR_POLYS-", "Points")
          #target_points_previous = target_points_previous.replace("-QUARTER-", Q0)

          feature.setAttribute("target_polys_current", target_poly_current)
          #feature.setAttribute("target_polys_previous", "")
          feature.setAttribute("target_points_current", target_points_current)
          #feature.setAttribute("target_points_previous", "")

          previous_points_SQL = sql_template.replace("-POINTS_OR_POLYS-", "Points")
          previous_polys_SQL = sql_template.replace("-POINTS_OR_POLYS-", "Polys")
          feature.setAttribute("previous_polys_SQL", previous_polys_SQL)
          feature.setAttribute("previous_points_SQL", previous_points_SQL)


          pass
    PYTHONSYMBOL = processFeature

Bookmark: Post-process
StringPadder_2
    BLANK_ATTRIBUTE = Yes
    PADCHAR = 0
    SIDE = Left
    SRC_ATTRS = FIPS
    WIDTH = 5
Tester
    BOOL_OP = OR
    TEST_CLAUSE:
      TEST Cur Pnt Cnt ATTRIBUTE_IS_EMPTY ""
      TEST Cur Pnt Cnt ATTRIBUTE_IS_MISSING ""
    TEST_MODE = TEST
Tester_2
    BOOL_OP = OR
    TEST_CLAUSE:
      TEST Cur Pnt Qual ATTRIBUTE_IS_EMPTY ""
      TEST Cur Pnt Qual ATTRIBUTE_IS_MISSING ""
    TEST_MODE = TEST
Tester_3
    BOOL_OP = OR
    TEST_CLAUSE:
      TEST Cur Poly Cnt ATTRIBUTE_IS_EMPTY ""
      TEST Cur Poly Cnt ATTRIBUTE_IS_MISSING ""
    TEST_MODE = TEST
Tester_4
    BOOL_OP = OR
    TEST_CLAUSE:
      TEST Cur Poly Qual ATTRIBUTE_IS_EMPTY ""
      TEST Cur Poly Qual ATTRIBUTE_IS_MISSING ""
    TEST_MODE = TEST
AttributeCreator
    ATTR_TABLE = SET_TO Cur Pnt Cnt = 0
AttributeCreator_2
    ATTR_TABLE = SET_TO Cur Pnt Qual = 0
AttributeCreator_3
    ATTR_TABLE = SET_TO Cur Poly Cnt = 0
AttributeCreator_4
    ATTR_TABLE = SET_TO Cur Poly Qual = 0
Tester_5
    BOOL_OP = OR
    TEST_CLAUSE:
      TEST Prv Pnt Cnt ATTRIBUTE_IS_EMPTY ""
      TEST Prv Pnt Cnt ATTRIBUTE_IS_MISSING ""
    TEST_MODE = TEST
Tester_6
    BOOL_OP = OR
    TEST_CLAUSE:
      TEST Prv Pnt Qual ATTRIBUTE_IS_EMPTY ""
      TEST Prv Pnt Qual ATTRIBUTE_IS_MISSING ""
    TEST_MODE = TEST
Tester_7
    BOOL_OP = OR
    TEST_CLAUSE:
      TEST Prv Poly Cnt ATTRIBUTE_IS_EMPTY ""
      TEST Prv Poly Cnt ATTRIBUTE_IS_MISSING ""
    TEST_MODE = TEST
Tester_8
    BOOL_OP = OR
    TEST_CLAUSE:
      TEST Prv Poly Qual ATTRIBUTE_IS_EMPTY ""
      TEST Prv Poly Qual ATTRIBUTE_IS_MISSING ""
    TEST_MODE = TEST
AttributeCreator_5
    ATTR_TABLE = SET_TO Prv Pnt Cnt = 0
AttributeCreator_6
    ATTR_TABLE = SET_TO Prv Pnt Qual = 0
AttributeCreator_7
    ATTR_TABLE = SET_TO Prv Poly Cnt = 0
AttributeCreator_8
    ATTR_TABLE = SET_TO Prv Poly Qual = 0
Junction_11

Bookmark: Search for previous tables
Note: allow nulls
Note: allow nulls
